Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase


'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strTemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strTemp = strTemp & vbNullChar
    Else
      strTemp = strTemp & strChar
    End If
  Next
  
  ' Put double null at end
  strTemp = strTemp & vbNullChar & vbNullChar
  of.lpstrFilter = strTemp
  
  ' Pad file and file title buffers to maximum path length
  strTemp = m_strFileName & String$(cintMaxFileLength - Len(m_strFileName), 0)
  of.lpstrFile = strTemp
  of.nMaxFile = cintMaxFileLength
  
  strTemp = m_strFileTitle & String$(cintMaxFileLength - Len(m_strFileTitle), 0)
  of.lpstrFileTitle = strTemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "CPoint2D"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public m_X As Double
Public m_Y As Double




Private Sub Class_Initialize()
    m_X = 0#
    m_Y = 0#
End Sub

Public Sub PlusVector(oVector As CVector2D)
    m_X = m_X + oVector.m_X
    m_Y = m_Y + oVector.m_Y
End Sub

Attribute VB_Name = "CVector2D"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit


Public m_X As Double
Public m_Y As Double




Private Sub Class_Initialize()
    m_X = 0#
    m_Y = 1#
End Sub

Public Sub Rotate(rotAngle As Double)
    Dim x As Double
    Dim y As Double
    x = m_X
    y = m_Y
    m_X = x * Cos(rotAngle) - y * Sin(rotAngle)
    m_Y = x * Sin(rotAngle) + y * Cos(rotAngle)
End Sub


Public Sub SetLength(length As Double)
    Dim x As Double
    Dim y As Double
    x = m_X
    y = m_Y

    m_X = m_X * length / GetLength()
    m_Y = m_Y * length / GetLength()
End Sub

Public Sub PlusVector(oVector As CVector2D)
    m_X = m_X + oVector.m_X
    m_Y = m_Y + oVector.m_Y
End Sub

Public Function GetLength() As Double
    GetLength = Sqr(m_X * m_X + m_Y * m_Y)
End Function

Public Sub ScaleV(value As Double)
    m_X = m_X * value
    m_Y = m_Y * value
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Public Const nFillIndex = 0
Public Const nCutIndex = 1
Public Const nNetIndex = 2
Public Const nLastIndex = nNetIndex




Public g_oVolumeDataArr(nLastIndex) As String

Function FormatVolumeSettings(ByVal dVolume As Double) As String
    Dim oVolumeSettings As AeccSettingsVolume
    Set oVolumeSettings = g_oAeccDb.settings.SurfaceSettings.AmbientSettings.VolumeSettings
        
    FormatVolumeSettings = FormatVolume(dVolume, oVolumeSettings.Unit, oVolumeSettings.Precision, oVolumeSettings.Rounding, oVolumeSettings.Sign)
End Function

Public Function ExtractData(oParcel As AeccParcel, oVolumeSurface As AeccSurface, filCor As Double, cutCor As Double) As Boolean
    Dim dCut As Double
    Dim dFill As Double
    Dim dNet As Double
    
    Dim arrBoundary() As Variant
    Dim oVolumeSurfaceStatics As Object
'   Dim oVolumeSurfaceStatics As AeccTinVolumeSurfaceStatistics
    'Dim oSurface As AeccTinVolumeSurface
    Dim oSurface As Object
    
    arrBoundary = GetBoundaryPtArr(oParcel.ParcelLoops(0))
    CleanBoundaryPtArr arrBoundary
    Set oSurface = oVolumeSurface
    Set oVolumeSurfaceStatics = oSurface.Statistics
    Dim newArr() As Double
    newArr = ResetPointArray(arrBoundary)
    oVolumeSurfaceStatics.BoundedVolumes newArr, dCut, dFill, dNet
    g_oVolumeDataArr(nFillIndex) = FormatVolumeSettings(dFill * filCor)
    g_oVolumeDataArr(nCutIndex) = FormatVolumeSettings(dCut * cutCor)
    g_oVolumeDataArr(nNetIndex) = FormatVolumeSettings(dFill * filCor - dCut * cutCor)
    ExtractData = True
End Function

Public Function GetBoundaryPtArr(oLoop As AeccParcelLoop) As Variant
    Dim bounds() As Variant
    Dim point(2) As Double

    Dim oSegment As AeccParcelSegmentElement
    Dim lPtCount As Long
    lPtCount = 0#
    For Each oSegment In oLoop
        If TypeOf oSegment Is AeccParcelSegmentCurve Then
            Dim arcPoints() As Variant
            Dim arcPtCounts As Long
            Dim iIter As Long
            arcPtCounts = GetArcSamplePoint(arcPoints, oSegment)
            lPtCount = lPtCount + arcPtCounts
            ReDim Preserve bounds(lPtCount - 1)
            For iIter = 1 To arcPtCounts Step 1
                bounds(lPtCount - arcPtCounts + iIter - 1) = arcPoints(iIter - 1)
            Next iIter
        Else
            point(0) = oSegment.startX
            point(1) = oSegment.startY
            point(2) = 0#
            lPtCount = lPtCount + 1
            ReDim Preserve bounds(lPtCount - 1)
            bounds(lPtCount - 1) = point
        End If
          
    Next
    point(0) = oLoop.Item(0).startX
    point(1) = oLoop.Item(0).startY
    point(2) = 0#
    lPtCount = lPtCount + 1
    ReDim Preserve bounds(lPtCount - 1)
    bounds(lPtCount - 1) = point
    GetBoundaryPtArr = bounds
    
    
End Function

' clean the duplicate line in the boundary
Private Sub CleanBoundaryPtArr(arrBoundary() As Variant)
    If UBound(arrBoundary) < 2 Then
        Exit Sub
    End If
    
    
    Dim i As Integer
    Dim pt1, pt2 As Variant
    For i = 0 To UBound(arrBoundary) - 2 Step 1
        pt1 = arrBoundary(i)        ' pt2's location is pt1+2
        pt2 = arrBoundary(i + 2)
        If pt1(0) = pt2(0) And pt1(1) = pt2(1) Then '
            GoTo Rebuild1
        End If
    Next
    pt1 = arrBoundary(UBound(arrBoundary) - 1) ' pt2 is the last 2nd, and pt1 is the 2nd in array.
    pt2 = arrBoundary(1)
    If pt1(0) = pt2(0) And pt1(1) = pt2(1) Then
        GoTo Rebuild2
    End If
    Exit Sub
Rebuild1:
    ReDim bounds(UBound(arrBoundary) - 2) As Variant
    Dim k As Integer
    For k = 0 To UBound(bounds) Step 1
        If k <= i Then
            bounds(k) = arrBoundary(k)
        Else
            bounds(k) = arrBoundary(k + 2)
        End If
    Next
    arrBoundary = bounds
    CleanBoundaryPtArr arrBoundary 'recursion
    Exit Sub
    
Rebuild2:
    ReDim bounds(UBound(arrBoundary) - 2) As Variant
    For k = 0 To UBound(bounds) Step 1
        bounds(k) = bounds(k + 1)
    Next
    CleanBoundaryPtArr arrBoundary 'recursion
    Exit Sub
    
End Sub

' return the count of sample Point
Private Function GetArcSamplePoint(oPoints() As Variant, oArc As AeccParcelSegmentCurve) As Long
    Dim ptCenter As New CPoint2D
    Dim ptStart As New CPoint2D
    Dim ptEnd As New CPoint2D
    Dim chordVector As New CVector2D
    Dim interval As Double
    
    ' initial value from curve segment
    ptStart.m_X = oArc.startX
    ptStart.m_Y = oArc.startY
    ptEnd.m_X = oArc.endX
    ptEnd.m_Y = oArc.EndY
    chordVector.m_X = ptEnd.m_X - ptStart.m_X
    chordVector.m_Y = ptEnd.m_Y - ptStart.m_Y
    
    ' get arc angle
    Dim rotAng As Double
    Dim halfAng As Double
    rotAng = oArc.length / oArc.Radius
    If oArc.Bulge > 0 Then
        halfAng = rotAng / 2
        interval = 0.2
    Else
        halfAng = -rotAng / 2
       interval = -0.2
    End If
    
    ' get the center of the arc
    Dim ptTemp As New CPoint2D
    Dim vecTemp As New CVector2D
    ptTemp.m_X = ptStart.m_X
    ptTemp.m_Y = ptStart.m_Y
    vecTemp.m_X = chordVector.m_X
    vecTemp.m_Y = chordVector.m_Y
    If oArc.Bulge > 0 Then
        Call vecTemp.Rotate(2 * Atn(1) - halfAng)
    Else
        Call vecTemp.Rotate(-2 * Atn(1) - halfAng)
    End If
    
    vecTemp.SetLength oArc.Radius
    ptTemp.PlusVector vecTemp
    ptCenter.m_X = ptTemp.m_X
    ptCenter.m_Y = ptTemp.m_Y
    
    vecTemp.ScaleV -1#
        
    ' get sample points
    Dim count As Long
    Dim pt(2) As Double
    Dim tmpAngle As Double
    Dim samplePt As New CPoint2D
    Dim vectSample As New CVector2D
    count = 1
    ReDim oPoints(0)
    pt(0) = oArc.startX
    pt(1) = oArc.startY
    pt(2) = 0#
    oPoints(0) = pt
    For tmpAngle = interval To 2 * halfAng Step interval
        vectSample.m_X = vecTemp.m_X
        vectSample.m_Y = vecTemp.m_Y
        vectSample.Rotate tmpAngle
        samplePt.m_X = ptCenter.m_X
        samplePt.m_Y = ptCenter.m_Y
        samplePt.PlusVector vectSample
        pt(0) = samplePt.m_X
        pt(1) = samplePt.m_Y
        pt(2) = 0#
        count = count + 1
        ReDim Preserve oPoints(count - 1)
        oPoints(count - 1) = pt
    Next tmpAngle
   
    GetArcSamplePoint = count
End Function

Public Function GetUnitStr() As String
    Dim settings
    Dim unitsStr As String
    
    Set settings = g_oAeccDb.settings.DrawingSettings.AmbientSettings.DistanceSettings.Unit
    If settings = AeccCoordinateUnitType.aeccCoordinateUnitFoot Then
        unitsStr = "Feet"
    ElseIf settings = AeccCoordinateUnitType.aeccCoordinateUnitMeter Then
        unitsStr = "Meters"
    End If
    GetUnitStr = unitsStr
End Function

Public Function ResetPointArray(oPoints() As Variant) As Double()
    Dim l As Long, u As Long, count As Long
    Dim newArr() As Double
    l = LBound(oPoints)
    u = UBound(oPoints)
    count = u - l + 1
    ReDim newArr(count * 3 - 1)
    Dim i As Long
    For i = l To u Step 1
        newArr(3 * (i - l)) = oPoints(i)(0)
        newArr(3 * (i - l) + 1) = oPoints(i)(1)
        newArr(3 * (i - l) + 2) = oPoints(i)(2)
    Next
    
    
    ResetPointArray = newArr

End Function

Attribute VB_Name = "ReportForm_ParcelVol"
Attribute VB_Base = "0{81F4FC75-92CE-4AE1-98D2-B94CF7D795E5}{564F51B8-CB60-4AB7-B047-52078DB2E529}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Const DefFilCorrection = "1"
Const DefCutCorrection = "1"
Const DefEleTolerance = "0.05"

Private g_parcelArr() As Variant
Private g_VolSurfaceArr() As Variant

Private g_sFileName As String
Private g_reportFileName As String
Private g_curParcel As AeccParcel
Private g_curVolSurface As AeccSurface

Private sCaptionArr() As String



Private Sub Combo_Surface_Change()
    Dim oSurface As AeccSurface
    Dim oTinVolSurface As AeccTinVolumeSurface
    Dim oGridVolSurface As AeccGridVolumeSurface
    
    Set oSurface = g_VolSurfaceArr(Combo_Surface.ListIndex)
    If oSurface.Type = aecckTinVolumeSurface Then
        Set g_curVolSurface = oSurface
        Set oTinVolSurface = oSurface
        Labe_Type.Caption = "Tin"
        Label_BaseSurface.Caption = oTinVolSurface.Statistics.BottomSurface.Name
        Label_CompSurface.Caption = oTinVolSurface.Statistics.TopSurface.Name
        TextBox_Ele.Enabled = False
    ElseIf oSurface.Type = aecckGridVolumeSurface Then
        Set g_curVolSurface = oSurface
        Set oGridVolSurface = oSurface
        Labe_Type.Caption = "Grid"
        Label_BaseSurface.Caption = oGridVolSurface.Statistics.BottomSurface.Name
        Label_CompSurface.Caption = oGridVolSurface.Statistics.TopSurface.Name
        TextBox_Ele.Enabled = True
    End If
          
End Sub

Private Sub Combo_Parcel_Change()
    Set g_curParcel = g_parcelArr(Combo_Parcel.ListIndex)
End Sub


Private Sub HelpButton_Click()
    ReportsHH_hWnd = ReportsHtmlHelp(0, getReportsHelpFile, HH_HELP_CONTEXT, IDH_AECC_REPORTS_CREATE_PARCEL_VOLUMES_REPORT)
End Sub

Private Sub SelParcelButton_Click()
    Dim sSet As AcadSelectionSet         'Define sset as a SelectionSet object
    Dim oParcel As AeccParcel
    
    'Set sset to a new selection set named SS1 (the name doesn't matter here)
    
    On Error Resume Next
    If Not IsNull(ThisDrawing.SelectionSets.Item("Parcel")) Then
        Set sSet = ThisDrawing.SelectionSets.Item("Parcel")
     sSet.Delete
    End If
  
    Set sSet = ThisDrawing.SelectionSets.Add("Parcel")
   
    
    Me.Hide  'Hide the current dialog
    
    sSet.SelectOnScreen       'Prompt user to select objects
    ' continue select on screen until select nothing or select a single point
    Do While Not sSet.count = 0
        If sSet.count = 1 Then
            If TypeOf sSet.Item(0) Is AeccParcel Then
                Exit Do
            End If
        End If
        MsgBox "Please select only one Parcel."
        sSet.Clear
        sSet.SelectOnScreen       'Prompt user to select objects
    Loop
    
    
    If sSet.count = 1 Then
        Dim iNum As Long
        Set oParcel = sSet.Item(0)
        Combo_Parcel.Text = oParcel.Parent.Name + " - " + oParcel.Name
    End If
         
    Me.Show ' restore the dialog
End Sub

Private Sub TextBox_Cut_Exit(ByVal Cancel As MSForms.ReturnBoolean)
    On Error GoTo ErrHandle
    Dim correction As Double
    correction = val(TextBox_Cut.value)
    If correction >= 1# And correction <= 2# Then
        TextBox_Cut.value = str(correction)
        Exit Sub
    End If
ErrHandle:
    MsgBox "Please input the right number from 1.000 to 2.000"
    TextBox_Cut.value = DefCutCorrection
End Sub

Private Sub TextBox_Cut_KeyPress(ByVal KeyAscii As MSForms.ReturnInteger)
    If KeyAscii <> 8 And (KeyAscii < 48 Or KeyAscii > 57) And KeyAscii <> 46 Then
        Beep
        KeyAscii = 0
    End If
End Sub

Private Sub TextBox_Ele_Exit(ByVal Cancel As MSForms.ReturnBoolean)
    On Error GoTo ErrHandle
    Dim correction As Double
    correction = val(TextBox_Ele.value)
    If correction >= 0# And correction <= 1# Then
        TextBox_Ele.value = str(correction)
        Exit Sub
    End If
ErrHandle:
    MsgBox "Please input the right number from 0.000 to 1.000"
    TextBox_Ele.value = DefEleTolerance
End Sub

Private Sub TextBox_Fill_Exit(ByVal Cancel As MSForms.ReturnBoolean)
    On Error GoTo ErrHandle
    Dim correction As Double
    correction = val(TextBox_Fill.value)
    If correction >= 1# And correction <= 2# Then
        TextBox_Fill.value = str(correction)
        Exit Sub
    End If
ErrHandle:
    MsgBox "Please input the right number from 1.000 to 2.000"
    TextBox_Fill.value = DefFilCorrection
End Sub

Private Sub TextBox_Fill_KeyPress(ByVal KeyAscii As MSForms.ReturnInteger)
    If KeyAscii <> 8 And (KeyAscii < 48 Or KeyAscii > 57) And KeyAscii <> 46 Then
        Beep
        KeyAscii = 0
    End If
End Sub

Private Sub Frame5_Exit(ByVal Cancel As MSForms.ReturnBoolean)
    If Frame5.ActiveControl = TextBox_Fill Then
        TextBox_Fill_Exit Cancel
    ElseIf Frame5.ActiveControl = TextBox_Cut Then
        TextBox_Cut_Exit Cancel
    ElseIf Frame5.ActiveControl = TextBox_Ele Then
        TextBox_Ele_Exit Cancel
    End If
End Sub

' Initialize the main dialog
Private Sub UserForm_Initialize()

    Dim tempPath As String
    Dim oSite As AeccSite
    Dim oSurface As AeccSurface
    Dim oParcel As AeccParcel
    Dim nCurParcelIndex As Long
    Dim nCurVolSurfaceIndex As Long
    Dim nParcelCount As Long
    
    g_sFileName = g_oCivilApp.Path
    
    tempPath = Environ("temp")
    g_reportFileName = tempPath & "\civilreport.html"
    
' init controls
 
    
    ReportFileNameEdit.Text = g_reportFileName
  
    ' progress bar settings
    ProgressBar.Min = 0
    ProgressBar.Max = 100
    ProgressBar.Visible = False
    progressBarLabel.Visible = False
  
    
    'parcels
    nParcelCount = 0
    nCurParcelIndex = 0
    If g_oAeccDb.Sites.count = 0 Then
       GoTo NoObject
    End If
    For Each oSite In g_oAeccDb.Sites
        If oSite.Parcels.count > 0 Then
            nParcelCount = oSite.Parcels.count + nParcelCount
            ReDim Preserve g_parcelArr(nParcelCount - 1)
            For Each oParcel In oSite.Parcels
                Set g_parcelArr(nCurParcelIndex) = oParcel
                Combo_Parcel.AddItem (oSite.Name + " - " + oParcel.Name)
                nCurParcelIndex = nCurParcelIndex + 1
            Next
        End If
    Next
    If nParcelCount > 0 Then
        Combo_Parcel.ListIndex = 0
    Else
        GoTo NoObject
    End If
    
    ' volume surfaces
    nCurVolSurfaceIndex = 0
    For Each oSurface In g_oAeccDb.Surfaces
        If oSurface.Type = aecckGridVolumeSurface Or oSurface.Type = aecckTinVolumeSurface Then
            ReDim Preserve g_VolSurfaceArr(nCurVolSurfaceIndex)
            Set g_VolSurfaceArr(nCurVolSurfaceIndex) = oSurface
            Combo_Surface.AddItem (oSurface.Name)
            nCurVolSurfaceIndex = nCurVolSurfaceIndex + 1
       End If
    Next
    If nCurVolSurfaceIndex > 0 Then
        Combo_Surface.ListIndex = 0
    Else
        GoTo NoObject
    End If
 
    TextBox_Fill.value = DefFilCorrection
    TextBox_Cut.value = DefCutCorrection
    TextBox_Ele.value = DefEleTolerance
   
    Exit Sub
NoObject:
        MsgBox "No Volume Surfaces or Parcels in " & ThisDrawing.Name & " exist."
        Err.Number = 1
        Exit Sub
End Sub


' Do the real work of gnerating the report here
Private Sub ExecuteButton_Click()
'    Dim t, pbarInc, cCount As Integer
'    Dim oAlignment As AeccAlignment
'    Dim curListItem As ListItem
    Dim exeStr As String
    Dim fillCorrection As Double
    Dim cutCorrection As Double
    Dim eleTolerance As Double
'
'

    If g_curParcel Is Nothing Or g_curVolSurface Is Nothing Then
        MsgBox "Please select a Parcel and a Volume Surface"
        Exit Sub
    End If
    
    progressBarLabel.Enabled = False
    progressBarLabel.Enabled = True

    progressBarLabel.Visible = True
    ProgressBar.Visible = True

    Call WriteReportHeader(g_reportFileName)
'
    'update progress bar
    ProgressBar.value = 10

    fillCorrection = val(TextBox_Fill.value)
    cutCorrection = val(TextBox_Cut.value)
    eleTolerance = val(TextBox_Ele.value)
    
    Call AppendReport(g_curParcel, g_curVolSurface, fillCorrection, cutCorrection, eleTolerance, g_reportFileName)
    'update progress bar
    ProgressBar.value = 100
'
    ProgressBar.Visible = False
    progressBarLabel.Visible = False
'
'
    Call WriteReportFooter(g_reportFileName)
'
    OpenFileByDefaultBrowser g_reportFileName

End Sub

Private Sub CancelButton_Click()

    Unload Me

End Sub




Private Sub UserForm_Terminate()

    ' clean up created objects
    Set g_oCivilApp = Nothing
    Set g_oAeccDoc = Nothing
    Set g_oAeccDb = Nothing
    Set g_curParcel = Nothing
    Set g_curVolSurface = Nothing
  
    
End Sub



Private Sub FileSelectionButton_Click()
    
    Dim fileDialog As New CFileDialog

    With fileDialog
        
        .DefaultExt = "html"

        .DialogTitle = "Select a HTML File"

        .Filter = "HTML Files|*.HTML"

        .FilterIndex = 1

        .MaxFileSize = 255

        .FileName = g_reportFileName
        
        If .Show(True) Then

            g_reportFileName = fileDialog.FileName
            ReportFileNameEdit.Text = g_reportFileName

        Else

            Exit Sub

        End If

    End With

End Sub

' Fill the data to Grid





Private Function GetDefaultInc() As Double
    Dim fInc As Double
    If GetUnitStr() = "Feet" Then
        fInc = 50#
    Else
        fInc = 25#
    End If
    GetDefaultInc = fInc
End Function

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Private g_tlbHeadArr() As String



Option Explicit
' Write the head of html file
Function WriteReportHeader(rptName As String) As Boolean
    Dim str As String
    Dim fs
    Dim ts As TextStream
    
    Set fs = CreateObject("Scripting.FileSystemObject")
    Set ts = fs.CreateTextFile(rptName, ForWriting, True)
    
    str = "<HTML title='Parcel Volume Report'><Body>"
    str = str & "<H1>Parcel Volume Report</H1>"
    ts.WriteLine (str)
    
    
    ' write owner and client setting
    WriteUserSetting ts
    
    str = "Date: " & DateTime.Month(DateTime.Date) & "-" & DateTime.Day(DateTime.Date) & "-" & DateTime.Year(DateTime.Date) & "<br/>"
    ts.WriteLine (str)
    ts.WriteLine ("<HR/>")
   
    ts.Close

   
    Set fs = Nothing
    Set ts = Nothing
    
    GetTableHead
    
    WriteReportHeader = True
End Function

' Write the end of html file
Function WriteReportFooter(rptName As String) As Boolean
    Dim str As String
    Dim fs, rf, ts
    
  
    Set fs = CreateObject("Scripting.FileSystemObject")
    Set rf = fs.GetFile(rptName)
    Set ts = rf.OpenAsTextStream(ForAppending, TristateUseDefault)

    str = "</Body></HTML>"
    
    ts.WriteLine (str)
    ts.Close

    Set ts = Nothing
    Set fs = Nothing
    Set rf = Nothing

    WriteReportFooter = True
End Function

' Append one item's report to html file
Function AppendReport(oParcel As AeccParcel, oVolumeSurface As AeccSurface, filCor As Double, cutCor As Double, eleTol As Double, rptName As String) As Boolean
    
    Dim str As String
    Dim fs, rf, ts
    Dim i As Integer


    Set fs = CreateObject("Scripting.FileSystemObject")
    Set rf = fs.GetFile(rptName)
    Set ts = rf.OpenAsTextStream(ForAppending, TristateUseDefault)

    ' alignment info
    str = str & "Parcel Name: " & oParcel.Parent.Name + " - " + oParcel.Name & "<br/>"
    str = str & "Description: " & oParcel.Description & "<br/>"
    str = str & "Volume Surface: " & oVolumeSurface.Name & "<br/>"
    str = str & "Fill correction: " & filCor & "<br/>"
    str = str & "Cut correction: " & cutCor & "<br/>"
    str = str & "Elevation Tolerance: " & eleTol & "<br/>"
    ts.Write (str)

    str = "<br><table border='1' width='100%' id='table1'>"
    str = str & "<b><tr><td>" _
          & g_tlbHeadArr(nFillIndex) & "</td> <td>" _
          & g_tlbHeadArr(nCutIndex) & "</td> <td>" _
          & g_tlbHeadArr(nNetIndex) & "</td> </tr></b>"

    str = str & "<HR/>"

    ts.Write (str)

    'extract data
    Call ExtractData(oParcel, oVolumeSurface, filCor, cutCor)

    ts.Write ("<b><tr> <td>" _
                & g_oVolumeDataArr(nFillIndex) & "</td> <td>" _
                & g_oVolumeDataArr(nCutIndex) & "</td> <td>" _
                & g_oVolumeDataArr(nNetIndex) _
                & "</td></tr></b>")

   
    ts.Write ("</Table><HR/>")

    ts.Close

    Set ts = Nothing
    Set fs = Nothing
    Set rf = Nothing
    
    AppendReport = True
End Function

Private Sub GetTableHead()
    ReDim g_tlbHeadArr(2)
    g_tlbHeadArr(nFillIndex) = "Fill Volume"
    g_tlbHeadArr(nCutIndex) = "Cut Volume"
    g_tlbHeadArr(nNetIndex) = "Net Volume"
End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub ParcelVol_RunReport()
    On Error Resume Next
    
    Dim rptDlg As ReportForm_ParcelVol
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_ParcelVol
    If Err.Number <> 0 Then
        Exit Sub
    End If
    rptDlg.Show

    
    Set rptDlg = Nothing
End Sub
