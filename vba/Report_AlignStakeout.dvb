Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase


'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strTemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strTemp = strTemp & vbNullChar
    Else
      strTemp = strTemp & strChar
    End If
  Next
  
  ' Put double null at end
  strTemp = strTemp & vbNullChar & vbNullChar
  of.lpstrFilter = strTemp
  
  ' Pad file and file title buffers to maximum path length
  strTemp = m_strFileName & String$(cintMaxFileLength - Len(m_strFileName), 0)
  of.lpstrFile = strTemp
  of.nMaxFile = cintMaxFileLength
  
  strTemp = m_strFileTitle & String$(cintMaxFileLength - Len(m_strFileTitle), 0)
  of.lpstrFileTitle = strTemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Enum StakeAngleType
    TurnedPlus
    TurnedMinus
    DeflectPlus
    DeflectMinus
    Direction
End Enum

Public Const nStationIndex = 0
Public Const nDirectionIndex = 1
Public Const nDistance = 2
Public Const nNorthingIndex = 3
Public Const nEastingIndex = 4
Public Const nLastIndex = nEastingIndex

Public g_angleType As StakeAngleType
Public g_staInc As Double
Public g_offSet As Double
Public g_oOccupiedPt As AeccPoint
Public g_oBacksightPt As AeccPoint

Public g_oAlignDataArr()
Function FormatCoordSettings(ByVal dDis As Double) As String
    Dim oCoordSettings As AeccSettingsCoordinate
    Set oCoordSettings = g_oAeccDb.settings.AlignmentSettings.AmbientSettings.CoordinateSettings
        
    FormatCoordSettings = FormatDistance(dDis, oCoordSettings.Unit.Value, oCoordSettings.Precision.Value, _
                oCoordSettings.Rounding.Value, oCoordSettings.Sign.Value)
End Function
Function FormatDistSettings(ByVal dDis As Double) As String
    Dim oDistSettings As AeccSettingsDistance
    Set oDistSettings = g_oAeccDb.settings.AlignmentSettings.AmbientSettings.DistanceSettings
    
    FormatDistSettings = FormatDistance(dDis, oDistSettings.Unit.Value, oDistSettings.Precision.Value, _
                oDistSettings.Rounding.Value, oDistSettings.Sign.Value)
End Function
Function FormatAngleSettings(ByVal dAngle As Double) As String
    Dim oAngleSettings As AeccSettingsAngle
    Set oAngleSettings = g_oAeccDb.settings.AlignmentSettings.AmbientSettings.AngleSettings

    FormatAngleSettings = FormatAngle(dAngle, oAngleSettings.Unit, oAngleSettings.Precision, _
                                      oAngleSettings.Rounding, oAngleSettings.Format, oAngleSettings.Sign)
End Function
Function FormatDirSettings(ByVal dDirection As Double) As String
    Dim oDirSettings As AeccSettingsDirection
    Set oDirSettings = g_oAeccDb.settings.AlignmentSettings.AmbientSettings.DirectionSettings
    
    FormatDirSettings = FormatDirection(dDirection, oDirSettings.Unit.Value, oDirSettings.Precision.Value, _
                                        oDirSettings.Rounding.Value, oDirSettings.Format.Value, _
                                        oDirSettings.Direction.Value, oDirSettings.Capitalization.Value, _
                                        oDirSettings.Sign.Value, oDirSettings.MeasurementType.Value, oDirSettings.BearingQuadrant)
End Function

Public Function ExtractData(oAlignment As AeccAlignment, stationStart As Double, stationEnd As Double) As Boolean
    Dim oDataArr(nLastIndex) As Variant
    Dim sStations As AeccAlignmentStations
    Dim oStation As AeccAlignmentStation
    Dim nCur As Integer
    
    
    Set sStations = oAlignment.GetStations(aeccAll, g_staInc, g_staInc)
    ReDim g_oAlignDataArr(sStations.Count)
    nCur = 0
    
    For Each oStation In sStations
            With oStation
                If .Type = aeccMajor Or .Type = aeccMinor Or .Station = oAlignment.StartingStation Then
                    If oStation.Station >= stationStart And oStation.Station <= stationEnd Then
                        Dim reportPtNorthing As Double, reportPtEasting As Double
                        ' Get reported Point using offset
                        oAlignment.PointLocation .Station, g_offSet, reportPtEasting, reportPtNorthing
                        
                        oDataArr(nStationIndex) = oAlignment.GetStationStringWithEquations(.Station)
                        oDataArr(nDirectionIndex) = GetDirectAngleInfo(reportPtNorthing, reportPtEasting)
                        oDataArr(nDistance) = FormatDistSettings(CalcDist(reportPtNorthing, reportPtEasting, g_oOccupiedPt.Northing, g_oOccupiedPt.Easting))
                        oDataArr(nNorthingIndex) = FormatCoordSettings(reportPtNorthing)
                        oDataArr(nEastingIndex) = FormatCoordSettings(reportPtEasting)
                        g_oAlignDataArr(nCur) = oDataArr
                        nCur = nCur + 1
                    End If
                End If
            End With
    Next
    

    ExtractData = True
End Function

Private Function GetDirectAngleInfo(dPtNorthing As Double, dPtEasting As Double) As String
    Dim sResult As String
    If g_angleType = Direction Then
        Dim rawDirNAzimuth As Double
        rawDirNAzimuth = CalcDirRad(g_oOccupiedPt.Northing, g_oOccupiedPt.Easting, dPtNorthing, dPtEasting)
        sResult = FormatDirSettings(2 * Atn(1) - rawDirNAzimuth) ' frome N Azimuth to x axis based.
 '       sResult = Get2PointDirData(g_oOccupiedPt.Northing, g_oOccupiedPt.Easting, dPtNorthing, dPtEasting, 2, cDMS, Bearing)
    Else
        Dim rawAngle As Double
        rawAngle = Calc3PointAngle(g_oOccupiedPt.Northing, g_oOccupiedPt.Easting, _
                                   dPtNorthing, dPtEasting, _
                                   g_oBacksightPt.Northing, g_oBacksightPt.Easting, g_angleType)
        sResult = FormatAngleSettings(rawAngle)
'        sResult = Report_Utilities.Utilities.FormatAngle(rawAngle, cDMS)
    End If
    GetDirectAngleInfo = sResult
End Function


Public Function GetUnitStr() As String
    Dim settings
    Dim unitsStr As String
    
    Set settings = g_oAeccDb.settings.DrawingSettings.AmbientSettings.DistanceSettings.Unit
    If settings = AeccCoordinateUnitType.aeccCoordinateUnitFoot Then
        unitsStr = "Feet"
    ElseIf settings = AeccCoordinateUnitType.aeccCoordinateUnitMeter Then
        unitsStr = "Meters"
    End If
    GetUnitStr = unitsStr
End Function

Attribute VB_Name = "ReportForm_AlignStakeout"
Attribute VB_Base = "0{438F340B-BFB7-40AF-8924-D9F1330BC3DE}{794D901F-1354-4A8D-8225-6805527BCDFC}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Private g_oAlignment As AeccAlignment
Private g_StartStation As Double
Private g_EndStation As Double
Private g_sFileName As String
Private g_reportFileName As String


Private Const nIncludeIndex = 0
Private Const nNameIndex = 1
Private Const nDescriptionIndex = 2
Private Const nStationStartIndex = 3
Private Const nStationEndIndex = 4
Private Const nLastIndex = nStationEndIndex

Private sCaptionArr() As String
Private g_alignArr()
Private pointDict As Dictionary



Private Sub HelpButton_Click()
    ReportsHH_hWnd = ReportsHtmlHelp(0, getReportsHelpFile, HH_HELP_CONTEXT, IDH_AECC_REPORTS_CREATE_STAKEOUT_ALIGNMENT_REPORT)
End Sub

' Initialize the main dialog
Private Sub UserForm_Initialize()

    Dim tempPath As String


    g_sFileName = g_oCivilApp.Path

    tempPath = Environ("temp")
    g_reportFileName = tempPath & "\civilreport.html"

' get the point dictionary from current drawing database
    If g_oAeccDb.Points.Count < 2 Then
        MsgBox "At least 2 Points exist in current drawing!"
        Err.Number = 1
        Exit Sub
    End If

    Dim iIndex As Integer
    Dim currentPoint As AeccPoint
    Set pointDict = New Dictionary
    For iIndex = 0 To g_oAeccDb.Points.Count - 1
        Set currentPoint = g_oAeccDb.Points.Item(iIndex)
        If Not currentPoint Is Nothing And Not pointDict.Exists(currentPoint.Number) Then
            pointDict.Add currentPoint.Number, currentPoint
        End If
    Next iIndex
    
    If pointDict.Count < 2 Then
        MsgBox "At least 2 Points exist in current drawing!"
        Err.Number = 1
        Exit Sub
    End If

' set report options here
    g_staInc = GetDefaultInc()
    g_offSet = 0#
' set angle type option here
    OptionTurnedPuls.Value = True
    g_angleType = TurnedPlus
    
' init controls
    StaIncEdit.Value = CStr(g_staInc)
    OffsetEdit.Value = CStr(g_offSet)
    
    ReportFileNameEdit.Text = g_reportFileName

    ' progress bar settings
    ProgressBar.min = 0
    ProgressBar.Max = 100
    ProgressBar.Visible = False
    progressBarLabel.Visible = False


    ' Get Captions
    GetCaptions

    ' list view grid setup
    ' setup columns
    Call ListView.ColumnHeaders.Add(, , sCaptionArr(nIncludeIndex), 40, lvwColumnLeft)
    Call ListView.ColumnHeaders.Add(, , sCaptionArr(nNameIndex), 100, lvwColumnLeft)
    Call ListView.ColumnHeaders.Add(, , sCaptionArr(nDescriptionIndex), 100, lvwColumnLeft)
    Call ListView.ColumnHeaders.Add(, , sCaptionArr(nStationStartIndex), 80, lvwColumnLeft)
    Call ListView.ColumnHeaders.Add(, , sCaptionArr(nStationEndIndex), 80, lvwColumnLeft)

    FillGrid

    StartStaEdit.Enabled = False
    EndStaEdit.Enabled = False

End Sub
''
' Radio button for angle type
Private Sub OptionDeflectMinus_Click()
    g_angleType = DeflectMinus
End Sub

Private Sub OptionDeflectPlus_Click()
    g_angleType = DeflectPlus
End Sub

Private Sub OptionDirection_Click()
    g_angleType = Direction
End Sub

Private Sub OptionTurnedMinus_Click()
    g_angleType = TurnedMinus
End Sub

Private Sub OptionTurnedPuls_Click()
    g_angleType = TurnedPlus
End Sub

Private Sub PointOccupiedEdit_KeyPress(ByVal KeyAscii As ReturnInteger)

    If KeyAscii <> 8 And KeyAscii < 48 Or KeyAscii > 57 Then
        Beep
        KeyAscii = 0
    End If
End Sub
Private Sub PointOccupiedEdit_Exit(ByVal Cancel As ReturnBoolean)
    Dim oPoints As AeccPoints
    
    If PointOccupiedEdit.Value = "" Then
        Exit Sub
    End If
        
    If pointDict.Exists(CLng(PointOccupiedEdit.Value)) Then
        Set g_oOccupiedPt = pointDict.Item(CLng(PointOccupiedEdit.Value))
    Else
        MsgBox "Please input the correct Point Number"
        If g_oOccupiedPt Is Nothing Then
            PointOccupiedEdit.Value = ""
        Else
            PointOccupiedEdit.Value = g_oOccupiedPt.Number
        End If
    End If
    
End Sub

Private Sub BacksightPointEdit_KeyPress(ByVal KeyAscii As ReturnInteger)
    If KeyAscii <> 8 And KeyAscii < 48 Or KeyAscii > 57 Then
        Beep
        KeyAscii = 0
    End If
End Sub
Private Sub BacksightPointEdit_Exit(ByVal Cancel As ReturnBoolean)
    Dim oPoints As AeccPoints
    
    If BacksightPointEdit.Value = "" Then
        Exit Sub
    End If
    
    If pointDict.Exists(CLng(BacksightPointEdit.Value)) Then
        Set g_oBacksightPt = pointDict.Item(CLng(BacksightPointEdit.Value))
    Else
        MsgBox "Please input the correct Point Number"
        If g_oBacksightPt Is Nothing Then
            BacksightPointEdit.Value = ""
        Else
            BacksightPointEdit.Value = g_oBacksightPt.Number
        End If
    End If
    
End Sub

Private Sub FrameStakeout_Exit(ByVal Cancel As ReturnBoolean)
    If FrameStakeout.ActiveControl = PointOccupiedEdit Then
        PointOccupiedEdit_Exit Cancel
    ElseIf FrameStakeout.ActiveControl = BacksightPointEdit Then
        BacksightPointEdit_Exit Cancel
    End If
End Sub

Private Sub Frame3_Exit(ByVal Cancel As MSForms.ReturnBoolean)
    If Frame3.ActiveControl = StartStaEdit Then
        StartStaEdit_Exit Cancel
    ElseIf Frame3.ActiveControl = EndStaEdit Then
        EndStaEdit_Exit Cancel
    End If
End Sub

Private Sub BacksightButton_Click()
    Dim sSet As AcadSelectionSet         'Define sset as a SelectionSet object
    Dim oPoint As AeccPoint
    'Set sset to a new selection set named SS1 (the name doesn't matter here)
    
    On Error Resume Next
    If Not IsNull(ThisDrawing.SelectionSets.Item("Points")) Then
        Set sSet = ThisDrawing.SelectionSets.Item("Points")
     sSet.Delete
    End If
  
    Set sSet = ThisDrawing.SelectionSets.Add("Points")
   
    
    Me.Hide  'Hide the current dialog
    
    sSet.SelectOnScreen       'Prompt user to select objects
    ' continue select on screen until select nothing or select a single point
    Do While Not sSet.Count = 0
        If sSet.Count = 1 Then
            If TypeOf sSet.Item(0) Is AeccPoint Then
                Exit Do
            End If
        End If
        MsgBox "Please select only one point."
        sSet.Clear
        sSet.SelectOnScreen       'Prompt user to select objects
    Loop
    
    
    If sSet.Count = 1 Then
        Dim iNum As Long
        Set oPoint = sSet.Item(0)
        iNum = oPoint.Number
        Set g_oBacksightPt = pointDict.Item(iNum)
        BacksightPointEdit.Value = iNum
    End If
         
    Me.Show ' restore the dialog
End Sub

Private Sub OccupiedButton_Click()
    
    Dim sSet As AcadSelectionSet         'Define sset as a SelectionSet object
    Dim oPoint As AeccPoint
    'Set sset to a new selection set named SS1 (the name doesn't matter here)
    
    On Error Resume Next
    If Not IsNull(ThisDrawing.SelectionSets.Item("Points")) Then
        Set sSet = ThisDrawing.SelectionSets.Item("Points")
     sSet.Delete
    End If
  
    Set sSet = ThisDrawing.SelectionSets.Add("Points")
   
    
    Me.Hide  'Hide the current dialog
    
    sSet.SelectOnScreen       'Prompt user to select objects
    
    
   ' continue select on screen until select nothing or select a single point
    Do While Not sSet.Count = 0
        If sSet.Count = 1 Then
            If TypeOf sSet.Item(0) Is AeccPoint Then
                Exit Do
            End If
        End If
        MsgBox "Please select only one point."
        sSet.Clear
        sSet.SelectOnScreen       'Prompt user to select objects
    Loop
    
    
    If sSet.Count = 1 Then
        Dim iNum As Long
        Set oPoint = sSet.Item(0)
        iNum = oPoint.Number
        Set g_oOccupiedPt = pointDict.Item(iNum)
        PointOccupiedEdit.Value = iNum
    End If
         
    Me.Show ' restore the dialog
End Sub

Private Sub StaIncEdit_Change()

    On Error Resume Next
    If StaIncEdit.Value <> "" Then
        g_staInc = CDbl(StaIncEdit.Value)
        If Err Or g_staInc < 0# Then
            g_staInc = GetDefaultInc()
            StaIncEdit.Value = g_staInc
        End If
    End If

End Sub
'


Private Sub StaIncSpinner_SpinDown()

    If StaIncEdit.Value > 0 Then
        StaIncEdit.Value = StaIncEdit.Value - 1
    End If

End Sub

Private Sub StaIncSpinner_SpinUp()
    If StaIncEdit.Value < 999 Then
        StaIncEdit.Value = StaIncEdit.Value + 1
    End If
End Sub
Private Sub OffsetEdit_Change()
    On Error Resume Next

    If OffsetEdit.Value <> "" Then
        g_offSet = CDbl(OffsetEdit.Value)
        If Err Or g_offSet < 0# Then
            g_offSet = 0#
            OffsetEdit.Value = 0#
        End If
    End If
End Sub
Private Sub OffsetSpinner_SpinDown()

    If OffsetEdit.Value > 0 Then
        OffsetEdit.Value = OffsetEdit.Value - 1
    End If

End Sub

Private Sub OffsetSpinner_SpinUp()
    If OffsetEdit.Value < 999 Then
        OffsetEdit.Value = OffsetEdit.Value + 1
    End If
End Sub
' Do the real work of gnerating the report here
Private Sub ExecuteButton_Click()
    Dim t, cCount As Integer
    Dim pbarInc As Single
    Dim oAlignment As AeccAlignment
    Dim curListItem As ListItem
    Dim exeStr As String
    Dim inStartStation As Double
    Dim inEndStation As Double
    
    If VerifyBeforeExe = False Then
        Exit Sub
    End If
    
    If ListView.ListItems.Count = 0 Then
        Exit Sub
    End If

    ' check if the increment is too small
    If g_staInc < 0.01 Then
        MsgBox "The station increment value is invalid."
        Exit Sub
    End If
    
    For t = 1 To ListView.ListItems.Count
        If ListView.ListItems(t).Checked = True Then
            cCount = cCount + 1
        End If
    Next

    pbarInc = 90 / cCount
    
    progressBarLabel.Enabled = False
    progressBarLabel.Enabled = True

    progressBarLabel.Visible = True
    ProgressBar.Visible = True
    
    Call WriteReportHeader(g_reportFileName)

    'update progress bar
    ProgressBar.Value = 0

    For t = 1 To ListView.ListItems.Count
        Set curListItem = ListView.ListItems(t)
        If curListItem.Checked = True Then
            Set oAlignment = g_alignArr(curListItem.Index - 1)
            If Not oAlignment Is Nothing Then
                inStartStation = GetRawStation(curListItem.SubItems(nStationStartIndex))
                inEndStation = GetRawStation(curListItem.SubItems(nStationEndIndex))
                Call AppendReport(oAlignment, inStartStation, inEndStation, g_reportFileName)
                ProgressBar.Value = ProgressBar.Value + pbarInc
            End If
        End If
    Next

    'update progress bar
    ProgressBar.Value = 100

    ProgressBar.Visible = False
    progressBarLabel.Visible = False


    Call WriteReportFooter(g_reportFileName)

    OpenFileByDefaultBrowser g_reportFileName

End Sub
'
Private Sub CancelButton_Click()

    Unload Me

End Sub
'

'
Private Sub UserForm_Terminate()

    ' clean up created objects
    Set g_oCivilApp = Nothing
    Set g_oAeccDoc = Nothing
    Set g_oAeccDb = Nothing
    Set g_oAlignment = Nothing
    Set pointDict = Nothing
    Set g_oOccupiedPt = Nothing
    Set g_oBacksightPt = Nothing
    
End Sub
Private Sub ListView_ItemClick(ByVal Item As ListItem)
    'MsgBox ""
    StartStaEdit.Enabled = True
    EndStaEdit.Enabled = True
    StartStaEdit.Value = Item.SubItems(nStationStartIndex)
    EndStaEdit.Value = Item.SubItems(nStationEndIndex)
    g_StartStation = GetRawStation(StartStaEdit.Value)
    g_EndStation = GetRawStation(EndStaEdit.Value)
    Set g_oAlignment = g_alignArr(Item.Index - 1)
End Sub

Private Sub EndStaEdit_Change()
    Dim curListItem As ListItem
    Set curListItem = ListView.SelectedItem
    If Not curListItem Is Nothing Then
        curListItem.SubItems(nStationEndIndex) = EndStaEdit.Value
    End If
End Sub

Private Sub EndStaEdit_Exit(ByVal Cancel As MSForms.ReturnBoolean)
    On Error Resume Next
    Dim rawStation As Double
    Dim defaultStation As Double
    Dim curListItem As ListItem
    
    Set curListItem = ListView.SelectedItem
    If g_oAlignment Is Nothing Or curListItem Is Nothing Then
       StartStaEdit.Value = ""
       Exit Sub
    End If
    
    'verify the station is in right format
    rawStation = CDbl(EndStaEdit.Value)
    If Err Then
        Err.Clear
        rawStation = GetRawStation(EndStaEdit.Value)
        If Err Then
            MsgBox "Please input right format for station."
            rawStation = g_EndStation
        End If
    End If
    
    'verify the startStation >= default value
    If rawStation > GetRoundedStationVal(g_oAlignment.EndingStation, g_oAlignment) Or rawStation < g_StartStation Then
        MsgBox "The EndStation Value is out of range"
        rawStation = g_oAlignment.EndingStation
    End If
    g_EndStation = rawStation
    EndStaEdit.Value = g_oAlignment.GetStationStringWithEquations(rawStation)
End Sub

Private Sub EndStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub

Private Sub StartStaEdit_Change()
    Dim curListItem As ListItem
    Set curListItem = ListView.SelectedItem
    If Not curListItem Is Nothing Then
        curListItem.SubItems(nStationStartIndex) = StartStaEdit.Value
    End If
End Sub

Private Sub StartStaEdit_Exit(ByVal Cancel As MSForms.ReturnBoolean)
    On Error Resume Next
    Dim rawStation As Double
    Dim defaultStation As Double
    Dim curListItem As ListItem

    Set curListItem = ListView.SelectedItem
    If g_oAlignment Is Nothing Or curListItem Is Nothing Then
       StartStaEdit.Value = ""
       Exit Sub
    End If

    'verify the station is in right format
    rawStation = CDbl(StartStaEdit.Value)
    If Err Then
        Err.Clear
        rawStation = GetRawStation(StartStaEdit.Value)
        If Err Then
            MsgBox "Please input right format for station."
            rawStation = g_StartStation
        End If
    End If

    'verify the startStation >= default value
    If rawStation > g_EndStation Or rawStation < GetRoundedStationVal(g_oAlignment.StartingStation, g_oAlignment) Then
        MsgBox "The StartStation Value is out of range"
        rawStation = g_oAlignment.StartingStation
    End If
    g_StartStation = rawStation
    StartStaEdit.Value = g_oAlignment.GetStationStringWithEquations(rawStation)
End Sub



Private Sub StartStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub
'


'
Private Sub FileSelectionButton_Click()

    Dim fileDialog As New CFileDialog

    With fileDialog

        .DefaultExt = "html"

        .DialogTitle = "Select a HTML File"

        .Filter = "HTML Files|*.HTML"

        .FilterIndex = 1

        .MaxFileSize = 255

        .FileName = g_reportFileName

        If .Show(True) Then

            g_reportFileName = fileDialog.FileName
            ReportFileNameEdit.Text = g_reportFileName

        Else

            Exit Sub

        End If

    End With

End Sub
'
'' Fill the data to Grid

Private Sub FillGrid()
    Dim oAlignment As AeccAlignment
    Dim oSite As AeccSite
    If g_oAeccDb.Sites.Count = 0 And g_oAeccDoc.AlignmentsSiteless.Count = 0 Then
       GoTo NoObject
    End If
    Dim li As ListItem
    Dim nCount As Long
    Dim nCurIndex As Long
    
    'get alignments from Document
    nCurIndex = 0
    nCount = g_oAeccDoc.AlignmentsSiteless.Count
    ReDim Preserve g_alignArr(nCount)
    For Each oAlignment In g_oAeccDoc.AlignmentsSiteless
        Set li = ListView.ListItems.Add
        li.SubItems(nNameIndex) = oAlignment.Name
        li.SubItems(nDescriptionIndex) = oAlignment.Description
        li.SubItems(nStationStartIndex) = oAlignment.GetStationStringWithEquations(oAlignment.StartingStation)
        li.SubItems(nStationEndIndex) = oAlignment.GetStationStringWithEquations(oAlignment.EndingStation)
        li.Checked = True
        Set g_alignArr(nCurIndex) = oAlignment
        nCurIndex = nCurIndex + 1
    Next
    
    'get alignments from Site
    For Each oSite In g_oAeccDb.Sites
        nCount = nCount + oSite.Alignments.Count
        ReDim Preserve g_alignArr(nCount)
        For Each oAlignment In oSite.Alignments
             Set li = ListView.ListItems.Add
             li.SubItems(nNameIndex) = oAlignment.Name
             li.SubItems(nDescriptionIndex) = oAlignment.Description
             li.SubItems(nStationStartIndex) = oAlignment.GetStationStringWithEquations(oAlignment.StartingStation)
             li.SubItems(nStationEndIndex) = oAlignment.GetStationStringWithEquations(oAlignment.EndingStation)
             li.Checked = True
             Set g_alignArr(nCurIndex) = oAlignment
             nCurIndex = nCurIndex + 1
        Next
    Next
    If nCount = 0 Then
        GoTo NoObject
    End If
    Exit Sub
NoObject:
        MsgBox "No alignments in " & ThisDrawing.Name & " exist."
        Err.Number = 1
End Sub

Private Sub GetCaptions()
    ReDim sCaptionArr(nLastIndex)
    sCaptionArr(nIncludeIndex) = "Include"
    sCaptionArr(nNameIndex) = "Name"
    sCaptionArr(nDescriptionIndex) = "Description"
    sCaptionArr(nStationStartIndex) = "Station Start"
    sCaptionArr(nStationEndIndex) = "Station End"
End Sub
'
Private Function GetDefaultInc() As Double
    Dim fInc As Double
    If GetUnitStr() = "Feet" Then
        fInc = 50#
    Else
        fInc = 25#
    End If
    GetDefaultInc = fInc
End Function

Private Function VerifyBeforeExe() As Boolean
    VerifyBeforeExe = False
    If g_oOccupiedPt Is Nothing Then
        MsgBox "Please select a occupied Point"
    ElseIf Not g_angleType = Direction Then
        If g_oBacksightPt Is Nothing Then
            MsgBox "Please select a backsight Point"
        ElseIf g_oOccupiedPt.Northing = g_oBacksightPt.Northing And g_oOccupiedPt.Easting = g_oBacksightPt.Easting Then
            MsgBox "The Backsight Point can not be the same as Occupied point"
        Else
            VerifyBeforeExe = True
        End If
    Else
        VerifyBeforeExe = True
    End If
End Function

Private Function GetRoundedStationVal(rawVal As Double, oAlignment As AeccAlignment) As Double
    GetRoundedStationVal = GetRawStation(oAlignment.GetStationStringWithEquations(rawVal))
End Function

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Private g_tlbHeadArr() As String



Option Explicit
' Write the head of html file
Function WriteReportHeader(rptName As String) As Boolean
    Dim str As String
    Dim unitsStr As String
    Dim fs
    Dim ts As TextStream
    
    Set fs = CreateObject("Scripting.FileSystemObject")
    Set ts = fs.CreateTextFile(rptName, ForWriting, True)
    
    str = "<HTML title='Stakeout Alignment Report'><Body>"
    str = str & "<H1>Stakeout Alignment Report</H1>"
    ts.WriteLine (str)
    
    
    ' write owner and client setting
    WriteUserSetting ts
    
    str = "Date: " & DateTime.Month(DateTime.Date) & "-" & DateTime.Day(DateTime.Date) & "-" & DateTime.Year(DateTime.Date) & "<br/>"
    ts.WriteLine (str)
    ts.WriteLine ("<HR/>")
   
    ts.Close

   
    Set fs = Nothing
    Set ts = Nothing
    
    GetTableHead
    
    WriteReportHeader = True
End Function

' Write the end of html file
Function WriteReportFooter(rptName As String) As Boolean
    Dim str As String
    Dim fs, rf, ts
    
  
    Set fs = CreateObject("Scripting.FileSystemObject")
    Set rf = fs.GetFile(rptName)
    Set ts = rf.OpenAsTextStream(ForAppending, TristateUseDefault)

    str = "</Body></HTML>"
    
    ts.WriteLine (str)
    ts.Close

    Set ts = Nothing
    Set fs = Nothing
    Set rf = Nothing

    WriteReportFooter = True
End Function

' Append one item's report to html file
Function AppendReport(oAlignment As AeccAlignment, stationStart As Double, stationEnd As Double, rptName As String) As Boolean
    Dim str As String
    Dim fs, rf, ts
    Dim i As Integer


    Set fs = CreateObject("Scripting.FileSystemObject")
    Set rf = fs.GetFile(rptName)
    Set ts = rf.OpenAsTextStream(ForAppending, TristateUseDefault)

    ' alignment info
    str = str & "Alignment Name: " & oAlignment.Name & "<br/>"
    str = str & "Description: " & oAlignment.Description & "<br/>"
    str = str & "Station Range: " & "Start: " & oAlignment.GetStationStringWithEquations(stationStart) _
                & ",  End: " & oAlignment.GetStationStringWithEquations(stationEnd) & "<br/>"
    'angle type
    str = str & "Stakeout Angle Type: " & GetStakeAngleTypeStr(g_angleType) & "<br/>"
    'Get occupied and backsight pt info
    str = str & "Occupied Pt: " & "<b>Northing </b>" & g_oOccupiedPt.Northing & "," & "<b>Easting </b>" & g_oOccupiedPt.Easting & "<br/>"
    If Not g_angleType = Direction Then
        str = str & "BackSight Pt: " & "<b>Northing </b>" & g_oBacksightPt.Northing & "," & "<b>Easting </b>" & g_oBacksightPt.Easting & "<br/>"
    End If
    'increment
    str = str & "Station interval: " & g_staInc & "<br/>"
    ' offset
    str = str & "OffSet: " & g_offSet & "<br/>"
    ts.Write (str)

    str = "<br><table border='1' width='100%' id='table1'>"
    str = str & "<b><tr><td>" _
          & g_tlbHeadArr(0) & "</td> <td>" _
          & g_tlbHeadArr(1) & "</td> <td>" _
          & g_tlbHeadArr(2) & "</td> <td>" _
          & g_tlbHeadArr(3) & "</td> <td>" _
          & g_tlbHeadArr(4) & "</td> </tr></b>"

    str = str & "<HR/>"

    ts.Write (str)

    'extract data
    Call ExtractData(oAlignment, stationStart, stationEnd)

    For i = 0 To UBound(g_oAlignDataArr)
        'Dim a As String
        'a = TypeName(g_oAlignDataArr(i))
        'Dim sTable As String
        'sTable = str
        If Not TypeName(g_oAlignDataArr(i)) = "Variant()" Then
            Exit For
        End If
        'format string
        Dim j
        Dim arrStr(nLastIndex)
        For j = 0 To nLastIndex
            arrStr(j) = CStr(VBA.Format(g_oAlignDataArr(i)(j), "0.00"))
        Next j

        ts.Write ("<b><tr> <td>" _
                    & arrStr(nStationIndex) & "</td> <td>" _
                    & arrStr(nDirectionIndex) & "</td> <td>" _
                    & arrStr(nDistance) & "</td> <td>" _
                    & arrStr(nNorthingIndex) & "</td> <td>" _
                    & arrStr(nEastingIndex) _
                    & "</td></tr></b>")

    Next
    ts.Write ("</Table><HR/>")

    ts.Close

    Set ts = Nothing
    Set fs = Nothing
    Set rf = Nothing
    
    AppendReport = True
End Function

Private Sub GetTableHead()
    ReDim g_tlbHeadArr(4)
    g_tlbHeadArr(0) = "Station"
    Select Case g_angleType
        Case TurnedPlus
            g_tlbHeadArr(1) = "Turned.Right"
        Case TurnedMinus
            g_tlbHeadArr(1) = "Turned.Left"
        Case DeflectPlus
            g_tlbHeadArr(1) = "Defl.Right"
        Case DeflectMinus
            g_tlbHeadArr(1) = "Defl.Left"
        Case Else     'Direction
            g_tlbHeadArr(1) = "Direction"
        End Select
    g_tlbHeadArr(2) = "Distance"
    g_tlbHeadArr(3) = "Coordinate.N"
    g_tlbHeadArr(4) = "Coordinate.E"
End Sub

Private Function GetStakeAngleTypeStr(aType As StakeAngleType) As String
    If aType = DeflectMinus Then
        GetStakeAngleTypeStr = "DeflectMinus"
    ElseIf aType = DeflectPlus Then
        GetStakeAngleTypeStr = "DeflectPlus"
    ElseIf aType = Direction Then
        GetStakeAngleTypeStr = "Direction"
    ElseIf aType = TurnedMinus Then
        GetStakeAngleTypeStr = "TurnedMinus"
    Else
        GetStakeAngleTypeStr = "TurnedPlus "
    End If
End Function

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub AlignStakeout_RunReport()
    On Error Resume Next
    
    Dim rptDlg As ReportForm_AlignStakeout
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_AlignStakeout
    If Err.Number <> 0 Then
        Exit Sub
    End If
    rptDlg.Show
    
    Set rptDlg = Nothing
End Sub
