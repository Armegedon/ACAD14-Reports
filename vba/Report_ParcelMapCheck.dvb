Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase

Public g_oSurveyApplication As AeccSurveyApplication
Public g_oSurveyDocument As AeccSurveyDocument
'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

'
'
' Function to set up the Civil 3D Survey application, document
' and database objects.
'
Function GetBaseSurveyObjects() As Boolean
    Dim oApp As AcadApplication
    Set oApp = ThisDrawing.Application
    Dim sAppName As String
    sAppName = "AeccXUiSurvey.AeccSurveyApplication"
    On Error Resume Next
    Set g_oSurveyApplication = oApp.GetInterfaceObject(sAppName)
    On Error GoTo 0
    If (g_oSurveyApplication Is Nothing) Then
        MsgBox "Error creating " & sAppName & ", exit."
        GetBaseSurveyObjects = False
        Exit Function
    End If
    Set g_oSurveyDocument = g_oSurveyApplication.ActiveDocument
    'Set g_oSurveyDatabase = g_oSurveyDocument.Database ' Do not need this currently
    GetBaseSurveyObjects = True
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strTemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strTemp = strTemp & vbNullChar
    Else
      strTemp = strTemp & strChar
    End If
  Next
  
  ' Put double null at end
  strTemp = strTemp & vbNullChar & vbNullChar
  of.lpstrFilter = strTemp
  
  ' Pad file and file title buffers to maximum path length
  strTemp = m_strFileName & String$(cintMaxFileLength - Len(m_strFileName), 0)
  of.lpstrFile = strTemp
  of.nMaxFile = cintMaxFileLength
  
  strTemp = m_strFileTitle & String$(cintMaxFileLength - Len(m_strFileTitle), 0)
  of.lpstrFileTitle = strTemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Public g_ParcelCheckData As New ParcelCheckData

Function FormatDistSettings_Parcel(ByVal dDis As Double) As String
    Dim oDistSettings As AeccSettingsDistance
    Set oDistSettings = g_oAeccDb.Settings.ParcelSettings.AmbientSettings.DistanceSettings
    
    FormatDistSettings_Parcel = FormatDistance(dDis, oDistSettings.Unit.Value, oDistSettings.precision.Value, _
                oDistSettings.Rounding.Value, oDistSettings.Sign.Value)
End Function

Function FormateCoordSettings_Parcel(ByVal dCoord As Double) As String
    Dim oCoordSettings As AeccSettingsCoordinate
    Set oCoordSettings = g_oAeccDb.Settings.ParcelSettings.AmbientSettings.CoordinateSettings
    
    FormateCoordSettings_Parcel = FormatDistance(dCoord, oCoordSettings.Unit.Value, oCoordSettings.precision.Value, _
                oCoordSettings.Rounding.Value, oCoordSettings.Sign.Value)
End Function

Function FormatDirSettings_Parcel(ByVal dDirection As Double) As String
    Dim oDirSettings As AeccSettingsDirection
    Set oDirSettings = g_oAeccDb.Settings.ParcelSettings.AmbientSettings.DirectionSettings
    
    FormatDirSettings_Parcel = FormatDirection(dDirection, oDirSettings.Unit.Value, oDirSettings.precision.Value, _
                                        oDirSettings.Rounding.Value, oDirSettings.Format.Value, _
                                        oDirSettings.Direction.Value, oDirSettings.Capitalization.Value, _
                                        oDirSettings.Sign.Value, oDirSettings.MeasurementType.Value, oDirSettings.BearingQuadrant)
End Function

Function FormatAngleSettings_Parcel(ByVal dAngle As Double) As String
    Dim oAngleSettings As AeccSettingsAngle
    Set oAngleSettings = g_oAeccDb.Settings.ParcelSettings.AmbientSettings.AngleSettings

    FormatAngleSettings_Parcel = FormatAngle(dAngle, oAngleSettings.Unit, oAngleSettings.precision, _
                                      oAngleSettings.Rounding, oAngleSettings.Format, oAngleSettings.Sign)
End Function

Function FormatAreaSettings_Parcel(ByVal dArea As Double) As String
    Dim oAreaSettings As AeccSettingsArea
    Set oAreaSettings = g_oAeccDb.Settings.ParcelSettings.AmbientSettings.areaSettings
    
    FormatAreaSettings_Parcel = FormatArea(dArea, oAreaSettings.Unit, oAreaSettings.precision.Value, _
                oAreaSettings.Rounding.Value, oAreaSettings.Sign.Value)
End Function

Function FormatDistSettings_Figure(ByVal dDis As Double) As String
    Dim oDistSettings As AeccSettingsDistance
    Dim oSurveySettings As AeccSurveySettingsRoot
    Set oSurveySettings = g_oSurveyDocument.Settings
    Set oDistSettings = oSurveySettings.SurveySettings.AmbientSettings.DistanceSettings
    
    FormatDistSettings_Figure = FormatDistance(dDis, oDistSettings.Unit.Value, oDistSettings.precision.Value, _
                oDistSettings.Rounding.Value, oDistSettings.Sign.Value)
End Function
Function FormatAreaSettings_Figure(ByVal dArea As Double) As String
    Dim oAreaSettings As AeccSettingsArea
    Set oAreaSettings = g_oAeccDb.Settings.ParcelSettings.AmbientSettings.areaSettings
    
    FormatAreaSettings_Figure = FormatArea(dArea, oAreaSettings.Unit, oAreaSettings.precision.Value, _
                oAreaSettings.Rounding.Value, oAreaSettings.Sign.Value)
End Function

'the return angle/direction is x axis based and counterclockwise
Function RoundDirection_Parcel(ByVal sNorth As Double, ByVal sEast As Double, ByVal eNorth As Double, ByVal eEast As Double) As Double
    Dim dirSettings As AeccSettingsDirection
    Dim tmpVal As Double
    Set dirSettings = g_oAeccDb.Settings.ParcelSettings.AmbientSettings.DirectionSettings
    tmpVal = 2 * Atn(1) - CalcDirRad(sNorth, sEast, eNorth, eEast)
    RoundDirection_Parcel = RoundVal(tmpVal, dirSettings.precision, dirSettings.Rounding)
End Function

Function RoundLength_Parcel(ByVal Length As Double) As Double
    Dim distSettings As AeccSettingsDistance
    Set distSettings = g_oAeccDb.Settings.ParcelSettings.AmbientSettings.DistanceSettings
    RoundLength_Parcel = RoundVal(Length, distSettings.precision, distSettings.Rounding)
End Function

' input angle is x-axis based
Sub CalculateNextPoint(ByVal curNorth As Double, ByVal curEast As Double, _
                               ByRef nextNorth As Double, ByRef nextEast As Double, _
                               ByVal dAngle As Double, ByVal dLength As Double)
    Dim polarsin As Double
    Dim polarcos As Double
    
    polarsin = Sin(dAngle)
    polarcos = Cos(dAngle)
    
    nextEast = curEast + dLength * polarcos
    nextNorth = curNorth + dLength * polarsin
End Sub


Public Function ExtractData(oParcel As AeccParcel, bCounterClockWise As Boolean, bAcrossChord As Boolean) As Boolean
    If oParcel.ParcelLoops.count <= 0 Then
        ExtractData = False
        Exit Function
    End If
    Dim oLoop As AeccParcelLoop
    Set oLoop = oParcel.ParcelLoops(0)
    If oParcel.ParcelLoops(0).count <= 0 Then
        ExtractData = False
        Exit Function
    End If
    
    'set segments data
    Dim segCount As Long
    Dim curIndex As Long
    
    'clean the segmentsData
    g_ParcelCheckData.Reset bCounterClockWise, bAcrossChord
    
    segCount = oLoop.count
    curIndex = 0
    Dim oCurSeg As AeccParcelSegmentElement
    Dim curNorth As Double, curEast As Double
    While curIndex < segCount
        If bCounterClockWise = False Then
            Set oCurSeg = oLoop(curIndex)
        Else
            Set oCurSeg = oLoop(segCount - curIndex - 1)
        End If
        
        If TypeOf oCurSeg Is AeccParcelSegmentLine Then
            g_ParcelCheckData.AddLine oCurSeg
        ElseIf TypeOf oCurSeg Is AeccParcelSegmentCurve Then
            g_ParcelCheckData.AddCurve oCurSeg
        Else
        End If
        
        curIndex = curIndex + 1
    Wend
    
    'Fill the left Datas
    g_ParcelCheckData.Area = oParcel.Statistics.Area
    g_ParcelCheckData.Perimeter = oParcel.Statistics.Perimeter
    
    ExtractData = True
    
End Function

Attribute VB_Name = "ParcelCheckData"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Private Segments As Collection
Private mCounterClockWise As Boolean
Private mAcrossChord As Boolean

Private mPOB_North As Double
Private mPOB_East As Double

Public Area As Double

Private mPerimeter As Double
Public Perimeter As Double




Public Property Get CounterClockWise() As Boolean
    CounterClockWise = mCounterClockWise
End Property

Public Property Get AcrossChord() As Boolean
    AcrossChord = mAcrossChord
End Property



Public Property Get POB_North() As Double
    POB_North = mPOB_North
End Property

Public Property Get POB_East() As Double
    POB_East = mPOB_East
End Property

Public Property Get SegmentCount() As Long
    SegmentCount = Segments.count
End Property

Public Function Item(index As Long) As Object
    Set Item = Segments.Item(index)
End Function

Public Sub Reset(couterClockWise As Boolean, AcrossChord As Boolean)
    Set Segments = New Collection
    mPOB_North = 0#
    mPOB_East = 0#
    mPerimeter = 0#
    Perimeter = 0#
    Area = 0#
    mCounterClockWise = couterClockWise
    mAcrossChord = AcrossChord
End Sub

Public Sub AddLine(oLine As AeccParcelSegmentLine)
    Dim segCount As Long
    Dim curNorth As Double, curEast As Double
    segCount = Segments.count
    If segCount = 0 Then
            If mCounterClockWise = False Then
                mPOB_North = oLine.StartY
                mPOB_East = oLine.StartX
            Else
                mPOB_North = oLine.EndY
                mPOB_East = oLine.EndX
            End If
            curNorth = mPOB_North
            curEast = mPOB_East
    Else
        curNorth = Segments(segCount).End_North
        curEast = Segments(segCount).End_East
    End If
    
    Dim segLine As New SegmentLine
    segLine.FillData curNorth, curEast, oLine, mCounterClockWise
    Segments.Add segLine
    mPerimeter = mPerimeter + segLine.Length
    
End Sub

Public Sub AddCurve(oCurve As AeccParcelSegmentCurve)
    Dim segCount As Long
    Dim curNorth As Double, curEast As Double
    segCount = Segments.count
    If segCount = 0 Then
            If mCounterClockWise = False Then
                mPOB_North = oCurve.StartY
                mPOB_East = oCurve.StartX
            Else
                mPOB_North = oCurve.EndY
                mPOB_East = oCurve.EndX
            End If
            curNorth = mPOB_North
            curEast = mPOB_East
    Else
        curNorth = Segments(segCount).End_North
        curEast = Segments(segCount).End_East
    End If
    
    Dim segCurve As New SegmentCurve
    segCurve.FillData curNorth, curEast, oCurve, mCounterClockWise, mAcrossChord
    Segments.Add segCurve
    If mAcrossChord = True Then
        mPerimeter = mPerimeter + segCurve.Chord
    Else
        mPerimeter = mPerimeter + segCurve.Length
    End If
End Sub

Private Sub Class_Initialize()
    Reset False, False
End Sub

Public Sub GetErrorInfo(ByRef Closure As Double, ByRef Course As Double, _
                        ByRef North As Double, ByRef East As Double, ByRef precision As Double)
    
    Dim count As Long
    count = Segments.count
    If count = 0 Then
        Exit Sub
    End If
    
    Dim endNorth As Double, endEast As Double
    endNorth = Segments(count).End_North
    endEast = Segments(count).End_East
    
    
    'Get Error Closure
    Dim dx As Double
    Dim dy As Double
    Dim distSettings As AeccSettingsDistance
    Dim coordSettings As AeccSettingsCoordinate
    Set distSettings = g_oAeccDb.Settings.ParcelSettings.AmbientSettings.DistanceSettings
    Set coordSettings = g_oAeccDb.Settings.ParcelSettings.AmbientSettings.CoordinateSettings
    dx = endEast - mPOB_East
    dy = endNorth - mPOB_North
    Closure = Sqr(dx * dx + dy * dy)
    Closure = RoundVal(Closure, coordSettings.precision, distSettings.Rounding)
    
    'Get Error Course
    Course = 2 * Atn(1) - CalcDirRad(mPOB_North, mPOB_East, endNorth, endEast)
   
    'Get Error North and East
    North = dy
    East = dx
    
    'Get Error Precision
    Dim errColsure As Double
    If Closure < 0.000001 Then
        errColsure = 0.000001
    Else
        errColsure = Closure
    End If
    precision = mPerimeter / errColsure
End Sub

Attribute VB_Name = "ReportForm_ParcelMapCheck"
Attribute VB_Base = "0{B2B727BE-1B06-4BFD-8729-6A781BCE915D}{FF46E255-A7FB-436D-9385-E1D341A1F5A2}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Private Type ParcelInfo
    Obj As AeccParcel
    CounterWiseClock As Boolean
    AcrossChord As Boolean
End Type

Private g_sFileName As String
Private g_reportFileName As String
Private g_pobXCoord As Double
Private g_pobYCoord As Double
Private g_isCounter As Boolean
Private g_EnableCheck As Boolean

Private g_bCheckParcle As Boolean

Private g_parcelArr() As ParcelInfo
Private g_figureArr() As AeccSurveyFigure

Private Const nIncludeIndex = 0
Private Const nNameIndex = 1
Private Const nNumberIndex = 2
Private Const nDescriptionIndex = 3
Private Const nAreaIndex = 4
Private Const nPerimeterIndex = 5
Private Const nLastIndex = nPerimeterIndex
Private sCaptionArr() As String

Private Sub Button_DeSelAll_Click()
    Dim lItem As ListItem
    If g_bCheckParcle = True Then
        For Each lItem In ListView_Parcels.ListItems
            lItem.Checked = False
        Next
    Else
        For Each lItem In ListView_Figures.ListItems
            lItem.Checked = False
        Next
    End If
End Sub

Private Sub Button_SelAll_Click()
    Dim lItem As ListItem
    If g_bCheckParcle = True Then
        For Each lItem In ListView_Parcels.ListItems
            lItem.Checked = True
        Next
    Else
        For Each lItem In ListView_Figures.ListItems
            lItem.Checked = True
        Next
    End If
End Sub

Private Sub CancelButton_Click()
    Unload Me
End Sub

Private Sub CheckAcrossChord_Click()
    Dim index As Integer
    index = ListView_Parcels.SelectedItem.index
    If index > 0 Then
        g_parcelArr(index - 1).AcrossChord = CheckAcrossChord.Value
    End If
End Sub

Private Sub CheckCounterClock_Click()
    Dim index As Integer
    index = ListView_Parcels.SelectedItem.index
    If index > 0 Then
        g_parcelArr(index - 1).CounterWiseClock = CheckCounterClock.Value
    End If
    
End Sub

Private Sub CommandButton1_Click()
    Me.Hide

    Dim selectPnt As Variant
    Dim prompt As String
    
    'Get AeccSettingCoordinate's decision
    Dim nDecision As Integer
    nDecision = g_oAeccDb.Settings.DrawingSettings.AmbientSettings.CoordinateSettings.precision
    On Error Resume Next

    prompt = vbCrLf & "Select Point of beginning: "
    selectPnt = ThisDrawing.Utility.GetPoint(, prompt)
    If Err Then
    Else
        Dim dXCoord As Double
        Dim dYCoord As Double
        dXCoord = CDbl(selectPnt(0))
        dYCoord = CDbl(selectPnt(1))
        PobXCoord.Text = RoundVal(dXCoord, nDecision)
        PobYCoord.Text = RoundVal(dYCoord, nDecision)
    End If
    
    Me.Show

End Sub

Private Sub ExecuteButton_Click()
    Dim t, cCount As Integer
    Dim pbarInc As Single
    Dim oParcel As AeccParcel
    Dim curListItem As ListItem
    Dim exeStr As String
    

    If ListView_Parcels.ListItems.count = 0 Then
        Exit Sub
    End If

    For t = 1 To ListView_Parcels.ListItems.count
        If ListView_Parcels.ListItems(t).Checked = True Then
            cCount = cCount + 1
        End If
    Next
'
    If cCount = 0 Then
        MsgBox "Please select at least one Parcel or Figure."
        Exit Sub
    End If
    pbarInc = 90 / cCount
'
    progressBarLabel.Enabled = False
    progressBarLabel.Enabled = True

    progressBarLabel.Visible = True
    ProgressBar.Visible = True
'
        'update progress bar
    ProgressBar.Value = 0
    
    Call WriteReportHeader(g_reportFileName)
'
    For t = 1 To ListView_Parcels.ListItems.count
        Set curListItem = ListView_Parcels.ListItems(t)
        If curListItem.Checked = True Then
            Set oParcel = g_parcelArr(t - 1).Obj
            If Not oParcel Is Nothing Then
                Call AppendReport(oParcel, g_parcelArr(t - 1).CounterWiseClock, g_parcelArr(t - 1).AcrossChord, g_reportFileName)
                ProgressBar.Value = ProgressBar.Value + pbarInc
            End If
        End If
    Next
'
    'update progress bar
    ProgressBar.Value = 100

    ProgressBar.Visible = False
    progressBarLabel.Visible = False


    Call WriteReportFooter(g_reportFileName)

    OpenFileByDefaultBrowser g_reportFileName


End Sub

Private Sub FileSelectionButton_Click()
    Dim fileDialog As New CFileDialog
    Dim a  As Double
    a = ListView_Parcels.top
    With fileDialog

        .DefaultExt = "html"

        .DialogTitle = "Select a HTML File"

        .Filter = "HTML Files|*.HTML"

        .FilterIndex = 1

        .MaxFileSize = 255

        .FileName = g_reportFileName

        If .Show(True) Then

            g_reportFileName = fileDialog.FileName
            ReportFileNameEdit.Text = g_reportFileName

        Else

            Exit Sub

        End If

    End With
End Sub

Private Sub HelpButton_Click()
    ReportsHH_hWnd = ReportsHtmlHelp(0, getReportsHelpFile, HH_HELP_CONTEXT, IDH_AECC_REPORTS_CREATE_PARCEL_MAPCHECK_REPORT)
End Sub







'Private Sub ListView_Parcels_AfterUpdate()
'    Dim selectedCount As Integer, i As Integer
'    selectedCount = 0
'    For i = 0 To ListView_Parcels.ListItems.count - 1 Step 1
'        If ListView_Parcels.ListItems(i).Selected = True Then
'            selectedCount = selectedCount + 1
'        End If
'    Next
'    If Not selectedCount = 1 Then
'        CheckCounterClock.Value = False
'        CheckCounterClock.Enabled = False
'        CheckAcrossChord.Value = False
'        CheckAcrossChord.Enabled = False
'        PobXCoord.Value = ""
'        PobYCoord.Value = ""
'    Else
'        Dim index As Integer
'        index = ListView_Parcels.SelectedItem.index
'        CheckCounterClock.Value = g_parcelArr(index).CounterWiseClock
'        CheckCounterClock.Enabled = True
'        CheckAcrossChord.Value = g_parcelArr(index).AcrossChord
'        CheckAcrossChord.Enabled = True
'    End If
'End Sub

Private Sub ListView_Parcels_ItemClick(ByVal Item As MSComctlLib.ListItem)
    Dim selectedCount As Integer, i As Integer
    selectedCount = 0
    For i = 1 To ListView_Parcels.ListItems.count Step 1
        If ListView_Parcels.ListItems(i).Selected = True Then
            selectedCount = selectedCount + 1
        End If
    Next
    If Not selectedCount = 1 Then
        CheckCounterClock.Value = False
        CheckCounterClock.Enabled = False
        CheckAcrossChord.Value = False
        CheckAcrossChord.Enabled = False
        PobXCoord.Value = ""
        PobYCoord.Value = ""
    Else
        Dim index As Integer
        index = ListView_Parcels.SelectedItem.index
        CheckCounterClock.Value = g_parcelArr(index - 1).CounterWiseClock
        CheckCounterClock.Enabled = True
        CheckAcrossChord.Value = g_parcelArr(index - 1).AcrossChord
        CheckAcrossChord.Enabled = True
        PobXCoord.Value = g_parcelArr(index - 1).Obj.ParcelLoops(0).Item(0).StartX
        PobYCoord.Value = g_parcelArr(index - 1).Obj.ParcelLoops(0).Item(0).StartY
    End If
End Sub

'Private Sub OptionButton_Figure_Change()
'    ListView_Parcels.Visible = False
'    ListView_Figures.Visible = True
''    ListView_Figures.top = ListView_Parcels.top
''    ListView_Figures.height = ListView_Parcels.height
''    ListView_Figures.left = ListView_Parcels.left
''    ListView_Figures.width = ListView_Parcels.width
''    Dim left As Single
''    left = Me.left + 0.4
''    Me.Move left
'End Sub

Private Sub OptionButton_Figure_Click()
    ListView_Figures.top = ListView_Parcels.top
    ListView_Figures.height = ListView_Parcels.height
    ListView_Figures.left = ListView_Parcels.left
    ListView_Figures.width = ListView_Parcels.width
    
'    ListView_Parcels.Enabled = False
    ListView_Parcels.Visible = False
'    ListView_Figures.Enabled = True
    ListView_Figures.Visible = True
    g_bCheckParcle = False
   
End Sub

'
'End Sub

Private Sub OptionButton_Parcel_Click()
 '   ListView_Figures.Enabled = False
    ListView_Figures.Visible = False
  '  ListView_Parcels.Enabled = True
    ListView_Parcels.Visible = True
   
  

    g_bCheckParcle = True
    
End Sub

Private Sub UserForm_Initialize()
    Dim tempPath As String

    
    g_sFileName = g_oCivilApp.Path

    tempPath = Environ("temp")
    g_reportFileName = tempPath & "\civilreport.html"


    
' init controls
   
    
    ReportFileNameEdit.Text = g_reportFileName

    ' progress bar settings
    ProgressBar.Min = 0
    ProgressBar.Max = 100
    ProgressBar.Visible = False
    progressBarLabel.Visible = False
    
    PobXCoord.Text = "0.000"
    PobYCoord.Text = "0.000"
    
    
    OptionButton_Parcel.Value = True
    'OptionButton_Figure.Value = True
    
    

        ' Get Captions
    GetCaptions

    ' list view grid setup
    ' setup columns
    Call ListView_Parcels.ColumnHeaders.Add(, , sCaptionArr(nIncludeIndex), 40, lvwColumnLeft)
    Call ListView_Parcels.ColumnHeaders.Add(, , sCaptionArr(nNameIndex), 100, lvwColumnRight)
    Call ListView_Parcels.ColumnHeaders.Add(, , sCaptionArr(nNumberIndex), 50, lvwColumnRight)
    Call ListView_Parcels.ColumnHeaders.Add(, , sCaptionArr(nDescriptionIndex), 80, lvwColumnRight)
    Call ListView_Parcels.ColumnHeaders.Add(, , sCaptionArr(nAreaIndex), 80, lvwColumnRight)
    Call ListView_Parcels.ColumnHeaders.Add(, , sCaptionArr(nPerimeterIndex), 80, lvwColumnRight)
    
    Call ListView_Figures.ColumnHeaders.Add(, , sCaptionArr(nIncludeIndex), 40, lvwColumnLeft)
    Call ListView_Figures.ColumnHeaders.Add(, , sCaptionArr(nNameIndex), 100, lvwColumnRight)
    Call ListView_Figures.ColumnHeaders.Add(, , sCaptionArr(nNumberIndex), 50, lvwColumnRight)
    Call ListView_Figures.ColumnHeaders.Add(, , sCaptionArr(nDescriptionIndex), 80, lvwColumnRight)
    Call ListView_Figures.ColumnHeaders.Add(, , sCaptionArr(nAreaIndex), 80, lvwColumnRight)
    Call ListView_Figures.ColumnHeaders.Add(, , sCaptionArr(nPerimeterIndex), 80, lvwColumnRight)
    
    FillSettings
    
    FillParcleGrid
    
'    If GetBaseSurveyObjects = True Then
'        FillFigureGrid
'    Else
'        OptionButton_Figure.Enabled = False
'    End If
    If ListView_Parcels.ListItems.count = 0 Then
        MsgBox "No parcels in " & ThisDrawing.Name & " exist."
        Err.Number = 1
    End If
    
End Sub

Private Sub GetCaptions()
    ReDim sCaptionArr(nLastIndex)
    sCaptionArr(nIncludeIndex) = "Include"
    sCaptionArr(nNameIndex) = "Name"
    sCaptionArr(nNumberIndex) = "Number"
    sCaptionArr(nDescriptionIndex) = "Description"
    sCaptionArr(nAreaIndex) = "Area"
    sCaptionArr(nPerimeterIndex) = "Perimeter"
End Sub


Private Sub FillParcleGrid()
    
    'Fill Parcel List View
    Dim oParcel As AeccParcel
    Dim oSite As AeccSite

    Dim li As ListItem
    Dim nCount As Long
    Dim nCurIndex As Long

    'get alignments from Site
    For Each oSite In g_oAeccDb.Sites
        nCount = nCount + oSite.Parcels.count
        ReDim Preserve g_parcelArr(nCount)
        For Each oParcel In oSite.Parcels
             Set li = ListView_Parcels.ListItems.Add
             li.SubItems(nNameIndex) = oParcel.Parent.Name + "-" + oParcel.Name
             li.SubItems(nNumberIndex) = oParcel.Number
             li.SubItems(nDescriptionIndex) = oParcel.Description
             li.SubItems(nAreaIndex) = FormatAreaSettings_Parcel(oParcel.Statistics.Area)
             li.SubItems(nPerimeterIndex) = FormatDistSettings_Parcel(oParcel.Statistics.Perimeter)
             li.Checked = True
             Set g_parcelArr(nCurIndex).Obj = oParcel
             g_parcelArr(nCurIndex).AcrossChord = False
             g_parcelArr(nCurIndex).CounterWiseClock = False
             nCurIndex = nCurIndex + 1
        Next
    Next

End Sub


Private Sub FillFigureGrid()
    Dim oFigure As AeccSurveyFigure
    Dim oProject As AeccSurveyProject
    
    Dim li As ListItem
    Dim nCount As Long
    Dim nCurIndex As Long

    'get alignments from Site
    For Each oProject In g_oSurveyDocument.Projects
        nCount = nCount + oProject.Figures.count
        ReDim Preserve g_figureArr(nCount)
        For Each oFigure In oProject.Figures
             Set li = ListView_Figures.ListItems.Add
             li.SubItems(nNameIndex) = oFigure.Name
             li.SubItems(nNumberIndex) = oFigure.Id
             li.SubItems(nDescriptionIndex) = ""
             li.SubItems(nAreaIndex) = FormatAreaSettings_Figure(0#)
             li.SubItems(nPerimeterIndex) = FormatDistSettings_Figure(0#)
             li.Checked = True
             Set g_figureArr(nCurIndex) = oFigure
             nCurIndex = nCurIndex + 1
        Next
    Next
    
End Sub

Private Sub FillSettings()
    Dim ambSettings As AeccSettingsAmbient
    Set ambSettings = g_oAeccDb.Settings.ParcelSettings.AmbientSettings

    Dim distFormat As String, dirFormat As String, coordFormat As String, areaFormat As String
    Select Case ambSettings.DirectionSettings.Format
        Case aeccFormatDecimal
            dirFormat = "(d)"
        Case aeccFormatDecimalDegreeMinuteSecond
            dirFormat = "DD.MMSSSS"
        Case aeccFormatDegreeMinuteSecond
            dirFormat = "DD" & Chr(176) & "MM" & Chr(176) & "SS"
        Case aeccFormatDegreeMinuteSecondSpaced
            dirFormat = "DD" & Chr(176) & " MM" & Chr(176) & " SS"
    End Select
    Label_DirecFormat.Caption = dirFormat
    Label_DistPrec.Caption = ambSettings.DistanceSettings.precision
    Label_DirePrec.Caption = ambSettings.DirectionSettings.precision
    Label_AreaPrec.Caption = ambSettings.areaSettings.precision
    Label_CloPrec.Caption = ambSettings.CoordinateSettings.precision
    Label_PrecPrec.Caption = ambSettings.DistanceSettings.precision
    
End Sub

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'


Option Explicit
' Write the head of html file
Function WriteReportHeader(rptName As String) As Boolean
    Dim str As String
    Dim fs
    Dim ts As TextStream
    
    Set fs = CreateObject("Scripting.FileSystemObject")
    Set ts = fs.CreateTextFile(rptName, ForWriting, True)
    
    str = "<HTML title='Parcel Map Check Report'><Body>"
    str = str & "<H1>Parcel Map Check Report</H1>"
    ts.WriteLine (str)
    
    
    ' write owner and client setting
    WriteUserSetting ts
    
    str = "Date: " & DateTime.Month(DateTime.Date) & "-" & DateTime.Day(DateTime.Date) & "-" & DateTime.Year(DateTime.Date) & "<br/>"
    ts.WriteLine (str)
    ts.WriteLine ("<HR/>")
   
    ts.Close

   
    Set fs = Nothing
    Set ts = Nothing
    
    WriteReportHeader = True
End Function

' Write the end of html file
Function WriteReportFooter(rptName As String) As Boolean
    Dim str As String
    Dim fs, rf, ts
    
  
    Set fs = CreateObject("Scripting.FileSystemObject")
    Set rf = fs.GetFile(rptName)
    Set ts = rf.OpenAsTextStream(ForAppending, TristateUseDefault)

    str = "</Body></HTML>"
    
    ts.WriteLine (str)
    ts.Close

    Set ts = Nothing
    Set fs = Nothing
    Set rf = Nothing

    WriteReportFooter = True
End Function

' Append one item's report to html file
Function AppendReport(oParcel As AeccParcel, bCounterClockWise As Boolean, bAcrossChord As Boolean, rptName As String) As Boolean
    Dim str As String
    Dim fs, rf
    Dim ts As TextStream
    Dim i As Integer
   
    If ExtractData(oParcel, bCounterClockWise, bAcrossChord) = False Then
        AppendReport = False
        Exit Function
    End If
    
    Set fs = CreateObject("Scripting.FileSystemObject")
    Set rf = fs.GetFile(rptName)
    Set ts = rf.OpenAsTextStream(ForAppending, TristateUseDefault)
    
    ' Parcel info
    str = str & "Parcel Name: " & oParcel.Parent.Name & "-" & oParcel.Name & "<br/>"
    str = str & "Description: " & oParcel.Description & "<br/>"
    ts.Write (str)
    str = "Process segment order counterclockwise: "
    If bCounterClockWise = True Then
        str = str + "True"
    Else
        str = str + "False"
    End If
    str = str + "<br/>"
    ts.Write str
    str = "Enable mapcheck across chord: "
    If bAcrossChord = True Then
        str = str + "True"
    Else
        str = str + "False"
    End If
    str = str + "<br/>"
    ts.Write str
    
    'POB
    str = "<br><table border='0' width='500' id='table1'>"
    ts.Write (str)
    
    Call AppendOneRecordInTable(ts, _
                                "North: " & FormateCoordSettings_Parcel(g_ParcelCheckData.POB_North), _
                                "East: " & FormateCoordSettings_Parcel(g_ParcelCheckData.POB_East))
    BreakLine ts
    'Segments
    Call AppendSegments(ts)
    
    'Check Error
    Call AppendCheckErrorInfo(ts)
    

    
    ts.Write ("</Table>")
    ts.WriteLine ("<br/>" & "<HR/>")
    ts.Close

    Set ts = Nothing
    Set fs = Nothing
    Set rf = Nothing
    
    AppendReport = True
    AppendReport = True
End Function

Private Sub AppendSegments(ts As TextStream)
    Dim i As Long
    Dim segCount As Long
    Dim seg As Object
    Dim segLine As SegmentLine
    Dim segCurve As SegmentCurve
    segCount = g_ParcelCheckData.SegmentCount
    
    For i = 1 To segCount Step 1
        Set seg = g_ParcelCheckData.Item(i)
        If TypeOf seg Is SegmentLine Then
            Set segLine = seg
            Call AppendOneRecordInTable(ts, "Segment#" + CStr(i) + " : Line", "&nbsp")
            Call AppendOneRecordInTable(ts, _
                                        "Course: " + FormatDirSettings_Parcel(segLine.Course), _
                                        "Length: " + FormatDistSettings_Parcel(segLine.Length))
            Call AppendOneRecordInTable(ts, _
                                        "North: " & FormateCoordSettings_Parcel(segLine.End_North), _
                                        "East: " & FormateCoordSettings_Parcel(segLine.End_East))
            
        Else
            Set segCurve = seg
            Call AppendOneRecordInTable(ts, "Segment#" + CStr(i) + " : Curve", "&nbsp")
            Call AppendOneRecordInTable(ts, _
                                        "Length: " & FormatDistSettings_Parcel(segCurve.Length), _
                                        "Radius: " & FormatDistSettings_Parcel(segCurve.Radius))
            Call AppendOneRecordInTable(ts, _
                                        "Delta: " & FormatAngleSettings_Parcel(segCurve.Delta), _
                                        "Tangent: " & FormatDistSettings_Parcel(segCurve.Tangent))
            Call AppendOneRecordInTable(ts, _
                                        "Chord: " & FormatDistSettings_Parcel(segCurve.Chord), _
                                        "Course: " & FormatDirSettings_Parcel(segCurve.Course))
            Call AppendOneRecordInTable(ts, _
                                        "Course In: " & FormatDirSettings_Parcel(segCurve.CourseIn), _
                                        "Course Out: " & FormatDirSettings_Parcel(segCurve.CourseOut))
            Call AppendOneRecordInTable(ts, _
                                        "RP North: " & FormateCoordSettings_Parcel(segCurve.RP_North), _
                                        "East: " & FormateCoordSettings_Parcel(segCurve.RP_East))
            Call AppendOneRecordInTable(ts, _
                                        "End North: " & FormateCoordSettings_Parcel(segCurve.End_North), _
                                        "East: " & FormateCoordSettings_Parcel(segCurve.End_East))
        End If
    
        BreakLine ts
    Next
   
    
End Sub

Private Sub AppendCheckErrorInfo(ts As TextStream)
    Dim ErrorClosure As Double
    Dim ErrorCourse As Double
    Dim ErrorNorth As Double, ErrorEast As Double
    Dim ErrorPrecision As Double
    
    g_ParcelCheckData.GetErrorInfo ErrorClosure, ErrorCourse, ErrorNorth, ErrorEast, ErrorPrecision
    
    
    Call AppendOneRecordInTable(ts, _
                                "Perimeter: " & FormatDistSettings_Parcel(g_ParcelCheckData.Perimeter), _
                                "Area: " & FormatAreaSettings_Parcel(g_ParcelCheckData.Area))
    'get Closure
    Dim coordPrecision As Integer
    Dim North As Double
    Dim East As Double
    coordPrecision = g_oAeccDb.Settings.ParcelSettings.AmbientSettings.CoordinateSettings.precision.Value
    North = RoundVal(ErrorNorth, coordPrecision + 1)
    East = RoundVal(ErrorEast, coordPrecision + 1)
    Call AppendOneRecordInTable(ts, _
                                "Error Closure: " & CStr(ErrorClosure), _
                                "Course: " & FormatDirSettings_Parcel(ErrorCourse))
    Call AppendOneRecordInTable(ts, _
                                "Error North : " & CStr(North), _
                                "East: " & CStr(East))
      
    BreakLine ts
    'Precision
    Dim distPrecision As Integer
    Dim prec As Double
    distPrecision = g_oAeccDb.Settings.ParcelSettings.AmbientSettings.DistanceSettings.precision.Value
    prec = RoundVal(ErrorPrecision, distPrecision)
    Call AppendOneRecordInTable(ts, _
                                "Precision " & "1:" & CStr(prec), _
                                "&nbsp")
End Sub

Private Sub AppendOneRecordInTable(ts As TextStream, str1 As String, str2 As String)
    Dim str As String
    str = "<b><tr><td>" _
          & str1 & "</td> <td>" _
          & str2 & "</td> </tr></b>"
    ts.Write (str)
End Sub

Private Sub BreakLine(ts As TextStream)
    AppendOneRecordInTable ts, "&nbsp", "&nbsp"
End Sub

Attribute VB_Name = "SegmentCurve"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public Length As Double
Public Radius As Double
Public Delta As Double
Public Tangent As Double
Public Chord As Double
Public Course As Double
Public CourseIn As Double
Public CourseOut As Double
Public RP_North As Double
Public RP_East As Double
Public End_North As Double
Public End_East As Double

Public Sub FillData(dStartNorth As Double, dStartEast As Double, oSegmentCurve As AeccParcelSegmentCurve, bCounterClockWise As Boolean, bAcrossChord As Boolean)
  
    'radius
    Radius = RoundLength_Parcel(oSegmentCurve.Radius)
    
    'Length
    Length = Radius * oSegmentCurve.Delta
    
    'delta
    Delta = oSegmentCurve.Delta
    
    'Tangent
    Tangent = Abs(oSegmentCurve.Tangent)
  
    
    'get real centerPoint
    Dim dirS2E As Double
    Dim dirS2C As Double
    Dim centerNorth As Double, centerEast As Double
    dirS2E = 2 * Atn(1) - CalcDirRad(oSegmentCurve.StartY, oSegmentCurve.StartX, oSegmentCurve.EndY, oSegmentCurve.EndX)
    dirS2C = dirS2E - 2 * Atn(1) + Delta / 2
    CourseIn = dirS2C
    CalculateNextPoint oSegmentCurve.StartY, oSegmentCurve.StartX, centerNorth, centerEast, dirS2C, oSegmentCurve.Radius
    
    'CourseIn and CourseOut
    Dim realSNorth As Double, realSEast As Double, realENorth As Double, realEEast As Double
    If bCounterClockWise = False Then
        realSNorth = oSegmentCurve.StartY
        realSEast = oSegmentCurve.StartX
        realENorth = oSegmentCurve.EndY
        realEEast = oSegmentCurve.EndX
    Else
        realSNorth = oSegmentCurve.EndY
        realSEast = oSegmentCurve.EndX
        realENorth = oSegmentCurve.StartY
        realEEast = oSegmentCurve.StartX
    End If
    CourseIn = RoundDirection_Parcel(realSNorth, realSEast, centerNorth, centerEast)
    CourseOut = RoundDirection_Parcel(centerNorth, centerEast, realENorth, realEEast)
    
    'chord length
    Chord = RoundLength_Parcel(Sqr((oSegmentCurve.EndY - oSegmentCurve.StartY) ^ 2 + (oSegmentCurve.EndX - oSegmentCurve.StartX) ^ 2))
    
    ' calculate the center of the arc for display
    CalculateNextPoint dStartNorth, dStartEast, RP_North, RP_East, CourseIn, Radius
    
    'chord Course
    Course = RoundDirection_Parcel(realSNorth, realSEast, realENorth, realEEast)
    
    ' perform map check across? to calculate End Pt
    If bAcrossChord = True Then
        CalculateNextPoint dStartNorth, dStartEast, End_North, End_East, Course, Chord
    Else
        CalculateNextPoint RP_North, RP_East, End_North, End_East, CourseOut, Radius
    End If
    
End Sub

Attribute VB_Name = "SegmentLine"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public Course As Double
Public Length As Double
Public End_North As Double
Public End_East As Double

Public Sub FillData(dStartNorth As Double, dStartEast As Double, oSegmentLine As AeccParcelSegmentLine, bCounterClockWise As Boolean)
    Dim tmpCourse As Double
    Dim roundedAngle As Double
    Dim roundedLength As Double
    
    tmpCourse = 2 * Atn(1) - CalcDirRad(oSegmentLine.StartY, oSegmentLine.StartX, oSegmentLine.EndY, oSegmentLine.EndX)
    roundedLength = RoundLength_Parcel(oSegmentLine.Length)
    If bCounterClockWise = False Then
        Course = tmpCourse
        roundedAngle = RoundDirection_Parcel(oSegmentLine.StartY, oSegmentLine.StartX, oSegmentLine.EndY, oSegmentLine.EndX)
        
    Else
        Course = -tmpCourse
        roundedAngle = RoundDirection_Parcel(oSegmentLine.EndY, oSegmentLine.EndX, oSegmentLine.StartY, oSegmentLine.StartX)
    End If
    CalculateNextPoint dStartNorth, dStartEast, End_North, End_East, roundedAngle, roundedLength
    Length = oSegmentLine.Length
End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub ParcelMapCheck_RunReport()
    On Error Resume Next
    
    Dim rptDlg As ReportForm_ParcelMapCheck
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_ParcelMapCheck
    If Err.Number <> 0 Then
        Exit Sub
    End If
    rptDlg.Show
    
    
    Set rptDlg = Nothing
End Sub
