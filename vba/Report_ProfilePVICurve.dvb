Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase


'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get flags() As Variant
  ' Returns: The flags
  ' Source: Total VB SourceBook 5

  flags = m_eFlags

End Property

Public Property Let flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strTemp As String
  
  On Error GoTo PROC_ERR
  
  ' Initialize the OPENFILENAME type
  of.lpstrTitle = m_strDialogTitle & ""
  of.flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strTemp = strTemp & vbNullChar
    Else
      strTemp = strTemp & strChar
    End If
  Next
  
  ' Put double null at end
  strTemp = strTemp & vbNullChar & vbNullChar
  of.lpstrFilter = strTemp
  
  ' Pad file and file title buffers to maximum path length
  strTemp = m_strFileName & String$(cintMaxFileLength - Len(m_strFileName), 0)
  of.lpstrFile = strTemp
  of.nMaxFile = cintMaxFileLength
  
  strTemp = m_strFileTitle & String$(cintMaxFileLength - Len(m_strFileTitle), 0)
  of.lpstrFileTitle = strTemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Public Const nStationIndex = 0
Public Const nElevationIndex = 1
Public Const nGradeOutIndex = 2
Public Const nCurveInfo = 3
Public Const nLastIndex = nCurveInfo

Public Const nCurvTypeIndex = 0
Public Const nPVCStationIndex = 1
Public Const nPVCElevationIndex = 2
Public Const nPVTStationIndex = 3
Public Const nPVTElevationIndex = 4
Public Const nHighStationIndex = 5
Public Const nHightElevation = 6
Public Const nLowStationIndex = 7
Public Const nLowElevation = 8
Public Const nGradeInIndex = 9
Public Const nGradeChange = 10
Public Const nCurveLenIndex = 11
Public Const nKIndex = 12
Public Const nHeadlightDisIndex = 13
Public Const nPassingDisIndex = 13
Public Const nStoppingDisIndex = 14
Public Const nLastCurInfoIndex = nStoppingDisIndex


Public g_oProfileDataArr()

Function FormatElevSettings(ByVal dDis As Double) As String
    Dim oElevSettings As AeccSettingsElevation
    Set oElevSettings = g_oAeccDb.settings.ProfileSettings.AmbientSettings.ElevationSettings
    
    FormatElevSettings = FormatDistance(dDis, oElevSettings.Unit.Value, oElevSettings.Precision.Value, _
                oElevSettings.Rounding.Value, oElevSettings.Sign.Value)
End Function
Function FormatDistSettings(ByVal dDis As Double) As String
    Dim oDistSettings As AeccSettingsDistance
    Set oDistSettings = g_oAeccDb.settings.ProfileSettings.AmbientSettings.DistanceSettings
    
    FormatDistSettings = FormatDistance(dDis, oDistSettings.Unit.Value, oDistSettings.Precision.Value, _
                oDistSettings.Rounding.Value, oDistSettings.Sign.Value)
End Function
Function FormatGradSettings(ByVal dGrad As Double) As String
    Dim oGradSettings As AeccSettingsGradeSlope
    Set oGradSettings = g_oAeccDb.settings.ProfileSettings.AmbientSettings.GradeSlopeSettings
    
    FormatGradSettings = FormatGrade(dGrad, oGradSettings.Format.Value, oGradSettings.Precision.Value, _
                oGradSettings.Rounding.Value, oGradSettings.Sign.Value)
End Function

Public Function ExtractData(oProfile As AeccProfile, stationStart As Double, stationEnd As Double) As Boolean
    Dim oDataArr(nLastIndex)
    Dim oPVI As AeccProfilePVI
    Dim oPVIC As AeccProfilePVICurve
    Dim nCur As Integer
    nCur = 0
    
    ReDim g_oProfileDataArr(oProfile.PVIs.Count - 1)
    ' Existing ground profile
    If oProfile.Type = aeccExistingGround Then
        For Each oPVI In oProfile.PVIs
            If oPVI.station >= stationStart And oPVI.station <= stationEnd Then
                Erase oDataArr
                oDataArr(nStationIndex) = oProfile.Alignment.GetStationStringWithEquations(oPVI.station)
                oDataArr(nElevationIndex) = FormatElevSettings(oPVI.Elevation)
                If oPVI.station = oProfile.EndingStation Then
                    oDataArr(nGradeOutIndex) = "&nbsp;"  'last One has no GradeOut Data
                Else
                    oDataArr(nGradeOutIndex) = FormatGradSettings(oPVI.GradeOut)
                End If
                g_oProfileDataArr(nCur) = oDataArr
                nCur = nCur + 1
            End If
        Next
    ' finished ground profile
    ElseIf oProfile.Type = aeccFinishedGround Then
    
        For Each oPVI In oProfile.PVIs
            On Error Resume Next
            Erase oDataArr
            If oPVI.station >= stationStart And oPVI.station <= stationEnd Then
                With oPVI
                    oDataArr(nStationIndex) = oProfile.Alignment.GetStationStringWithEquations(.station)
                    oDataArr(nElevationIndex) = FormatElevSettings(.Elevation)
                    oDataArr(nGradeOutIndex) = FormatGradSettings(.GradeOut)
                    If oDataArr(nGradeOutIndex) = Empty Then
                        oDataArr(nGradeOutIndex) = "&nbsp;"
                    End If
                End With
                ' get curve info
                
                Set oPVIC = Nothing
                Set oPVIC = oPVI
                If Not oPVIC Is Nothing Then
                    Dim oCurveDataArr(nLastCurInfoIndex)
                    Erase oCurveDataArr
                    oCurveDataArr(nCurvTypeIndex) = oPVIC.VerticalCurveType
                    oCurveDataArr(nPVCStationIndex) = oProfile.Alignment.GetStationStringWithEquations(oPVIC.BeginStation)
                    oCurveDataArr(nPVCElevationIndex) = FormatElevSettings(oPVIC.BeginElevation)
                    oCurveDataArr(nPVTStationIndex) = oProfile.Alignment.GetStationStringWithEquations(oPVIC.EndStation)
                    oCurveDataArr(nPVTElevationIndex) = FormatElevSettings(oPVIC.EndElevation)
                    oCurveDataArr(nHighStationIndex) = oProfile.Alignment.GetStationStringWithEquations(oPVIC.HighPointStation)
                    oCurveDataArr(nHightElevation) = FormatElevSettings(oPVIC.HighPointElevation)
                    oCurveDataArr(nLowStationIndex) = oProfile.Alignment.GetStationStringWithEquations(oPVIC.LowPointStation)
                    oCurveDataArr(nLowElevation) = FormatElevSettings(oPVIC.LowPointElevation)
                    If oPVI.station = oProfile.StartingStation Then
                        oCurveDataArr(nGradeInIndex) = "&nbsp;"
                    Else
                        oCurveDataArr(nGradeInIndex) = FormatGradSettings(oPVIC.GradeIn)
                    End If
                    oCurveDataArr(nGradeChange) = FormatGradSettings(oPVIC.GradeChange)
                    oCurveDataArr(nCurveLenIndex) = FormatDistSettings(oPVIC.CurveLength)
    '
                    If oPVIC.EntityType = aeccParabola Then
                        Dim oPVIPara As AeccProfilePVICurveParabolic
                        Set oPVIPara = oPVIC
                        oCurveDataArr(nKIndex) = oPVIPara.k
                        If oPVIC.VerticalCurveType = aeccSag Then
                            oCurveDataArr(nHeadlightDisIndex) = FormatDistSettings(oPVIPara.HeadlightSightDistance)
                        Else ' = aeccCrest
                            oCurveDataArr(nPassingDisIndex) = FormatDistSettings(oPVIPara.PassingSightDistance)
                            oCurveDataArr(nStoppingDisIndex) = FormatDistSettings(oPVIPara.StoppingSightDistance)
                        End If
                    End If
                    oDataArr(nCurveInfo) = oCurveDataArr
    
                End If
    
                g_oProfileDataArr(nCur) = oDataArr
                nCur = nCur + 1
            End If
        Next
    End If
    
    ExtractData = True
End Function

Attribute VB_Name = "ReportForm_ProfPVICurve"
Attribute VB_Base = "0{EFF730C5-8009-47DD-8687-A9181EAC5F53}{E6AB7177-EE63-4E68-9114-A1E9031DB389}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit




Private g_oProfile As AeccProfile
Private g_StartStation As Double
Private g_EndStation As Double
Private g_sFileName As String
Private g_reportFileName As String


Private Const nIncludeIndex = 0
Private Const nNameIndex = 1
Private Const nDescriptionIndex = 2
Private Const nStationStartIndex = 3
Private Const nStationEndIndex = 4
Private Const nAlignNameIndex = 5
Private Const nLastIndex = nAlignNameIndex

Private sCaptionArr() As String
Private g_profileArr()








Private Sub CancelButton_Click()
    Unload Me
End Sub

Private Sub HelpButton_Click()
    ReportsHH_hWnd = ReportsHtmlHelp(0, getReportsHelpFile, HH_HELP_CONTEXT, IDH_AECC_REPORTS_CREATE_PVI_STATION_AND_CURVE_REPORT)
End Sub

' Initialize the main dialog
Private Sub UserForm_Initialize()

    Dim tempPath As String

    
    g_sFileName = g_oCivilApp.Path

    tempPath = Environ("temp")
    g_reportFileName = tempPath & "\civilreport.html"


    
' init controls
   
    
    ReportFileNameEdit.Text = g_reportFileName

    ' progress bar settings
    ProgressBar.min = 0
    ProgressBar.Max = 100
    ProgressBar.Visible = False
    progressBarLabel.Visible = False


    ' Get Captions
    GetCaptions

    ' list view grid setup
    ' setup columns
    Call ListView.ColumnHeaders.Add(, , sCaptionArr(nIncludeIndex), 40, lvwColumnLeft)
    Call ListView.ColumnHeaders.Add(, , sCaptionArr(nNameIndex), 100, lvwColumnLeft)
    Call ListView.ColumnHeaders.Add(, , sCaptionArr(nDescriptionIndex), 100, lvwColumnLeft)
    Call ListView.ColumnHeaders.Add(, , sCaptionArr(nStationStartIndex), 80, lvwColumnLeft)
    Call ListView.ColumnHeaders.Add(, , sCaptionArr(nStationEndIndex), 80, lvwColumnLeft)
    Call ListView.ColumnHeaders.Add(, , sCaptionArr(nAlignNameIndex), 100, lvwColumnLeft)
    

    FillGrid
    
    If ListView.ListItems.Count > 0 Then
    '    ListView.ListItems(0).Selected = True  '.Selected = True
    '    ListView_ItemClick ListView.ListItems(0)
    End If
    
    StartStaEdit.Enabled = False
    EndStaEdit.Enabled = False
  ' ListView.ListItems(0).Selected = True
    'ListView.LabelEdit = lvwManual
  '  Set g_oAmbientSetting = g_oAeccDb.settings.DrawingSettings.AmbientSettings
End Sub
''

' Do the real work of gnerating the report here
Private Sub ExecuteButton_Click()
    Dim t, cCount As Integer
    Dim pbarInc As Single
    Dim oProfile As AeccProfile
    Dim curListItem As ListItem
    Dim exeStr As String
    Dim inStartStation As Double
    Dim inEndStation As Double
   
    If ListView.ListItems.Count = 0 Then
        Exit Sub
    End If

    For t = 1 To ListView.ListItems.Count
        If ListView.ListItems(t).Checked = True Then
            cCount = cCount + 1
        End If
    Next

    pbarInc = 90 / cCount

    progressBarLabel.Enabled = False
    progressBarLabel.Enabled = True

    progressBarLabel.Visible = True
    ProgressBar.Visible = True
    Call WriteReportHeader(g_reportFileName)

    'update progress bar
    ProgressBar.Value = 0

    For t = 1 To ListView.ListItems.Count
        Set curListItem = ListView.ListItems(t)
        If curListItem.Checked = True Then
            Set oProfile = g_profileArr(curListItem.Index - 1)
            If Not oProfile Is Nothing Then
                inStartStation = GetRawStation(curListItem.SubItems(nStationStartIndex))
                inEndStation = GetRawStation(curListItem.SubItems(nStationEndIndex))
                Call AppendReport(oProfile, inStartStation, inEndStation, g_reportFileName)
                ProgressBar.Value = ProgressBar.Value + pbarInc
            End If
        End If
    Next

    'update progress bar
    ProgressBar.Value = 100

    ProgressBar.Visible = False
    progressBarLabel.Visible = False


    Call WriteReportFooter(g_reportFileName)
    
    OpenFileByDefaultBrowser g_reportFileName

End Sub

'
Private Sub UserForm_Terminate()

    ' clean up created objects
    Set g_oProfile = Nothing
    Set g_oCivilApp = Nothing
    Set g_oAeccDoc = Nothing
    Set g_oAeccDb = Nothing
End Sub
'



'
Private Sub FileSelectionButton_Click()

    Dim fileDialog As New CFileDialog

    With fileDialog

        .DefaultExt = "html"

        .DialogTitle = "Select a HTML File"

        .Filter = "HTML Files|*.HTML"

        .FilterIndex = 1

        .MaxFileSize = 255

        .FileName = g_reportFileName

        If .Show(True) Then

            g_reportFileName = fileDialog.FileName
            ReportFileNameEdit.Text = g_reportFileName

        Else

            Exit Sub

        End If

    End With

End Sub
'
'' Fill the data to Grid

Private Sub FillGrid()
    Dim oSite As AeccSite
    Dim oAlignment As AeccAlignment
    Dim oProfile As AeccProfile
    If g_oAeccDb.Sites.Count = 0 Then
       GoTo NoObject
    End If
    Dim li As ListItem
    Dim nCount As Long
    Dim nCurIndex As Long
    'get alignments from Document
    nCurIndex = 0
    For Each oAlignment In g_oAeccDoc.AlignmentsSiteless
        nCount = nCount + oAlignment.Profiles.Count
        ReDim Preserve g_profileArr(nCount)
        For Each oProfile In oAlignment.Profiles
            If oProfile.Type = aeccFinishedGround Then
                Set li = ListView.ListItems.Add
                li.SubItems(nNameIndex) = oProfile.Name
                li.SubItems(nDescriptionIndex) = oProfile.Description
                li.SubItems(nStationStartIndex) = oAlignment.GetStationStringWithEquations(oProfile.StartingStation)
                li.SubItems(nStationEndIndex) = oAlignment.GetStationStringWithEquations(oProfile.EndingStation)
                li.SubItems(nAlignNameIndex) = oProfile.Alignment.Name
                li.Checked = True
                Set g_profileArr(nCurIndex) = oProfile
                nCurIndex = nCurIndex + 1
            End If
        Next
    Next
    'get alignments from Site
    For Each oSite In g_oAeccDb.Sites
        For Each oAlignment In oSite.Alignments
            nCount = nCount + oAlignment.Profiles.Count
            ReDim Preserve g_profileArr(nCount)
            For Each oProfile In oAlignment.Profiles
                If oProfile.Type = aeccFinishedGround Then
                    Set li = ListView.ListItems.Add
                    li.SubItems(nNameIndex) = oProfile.Name
                    li.SubItems(nDescriptionIndex) = oProfile.Description
                    li.SubItems(nStationStartIndex) = oAlignment.GetStationStringWithEquations(oProfile.StartingStation)
                    li.SubItems(nStationEndIndex) = oAlignment.GetStationStringWithEquations(oProfile.EndingStation)
                    li.SubItems(nAlignNameIndex) = oProfile.Alignment.Name
                    li.Checked = True
                    Set g_profileArr(nCurIndex) = oProfile
                    nCurIndex = nCurIndex + 1
                End If
            Next
        Next
    Next
    If nCurIndex = 0 Then
        GoTo NoObject
    End If
    Exit Sub
NoObject:
        MsgBox "No FG profiles in " & ThisDrawing.Name & " exist."
        Err.Number = 1
End Sub

Private Sub GetCaptions()
    ReDim sCaptionArr(nLastIndex)
    sCaptionArr(nIncludeIndex) = "Include"
    sCaptionArr(nNameIndex) = "Name"
    sCaptionArr(nDescriptionIndex) = "Description"
    sCaptionArr(nStationStartIndex) = "Station Start"
    sCaptionArr(nStationEndIndex) = "Station End"
    sCaptionArr(nAlignNameIndex) = "Alignment"
End Sub
'

Private Sub Frame3_Exit(ByVal Cancel As MSForms.ReturnBoolean)
    If Frame3.ActiveControl = StartStaEdit Then
        StartStaEdit_Exit Cancel
    ElseIf Frame3.ActiveControl = EndStaEdit Then
        EndStaEdit_Exit Cancel
    End If
End Sub

Private Sub ListView_ItemClick(ByVal Item As ListItem)
    'MsgBox ""
    StartStaEdit.Enabled = True
    EndStaEdit.Enabled = True
    StartStaEdit.Value = Item.SubItems(nStationStartIndex)
    EndStaEdit.Value = Item.SubItems(nStationEndIndex)
    g_StartStation = GetRawStation(StartStaEdit.Value)
    g_EndStation = GetRawStation(EndStaEdit.Value)
    Set g_oProfile = g_profileArr(Item.Index - 1)
End Sub

Private Sub StartStaEdit_Exit(ByVal Cancel As MSForms.ReturnBoolean)
    On Error Resume Next
    Dim rawStation As Double
    Dim defaultStation As Double
    Dim curListItem As ListItem
    
    Set curListItem = ListView.SelectedItem
    If g_oProfile Is Nothing Or curListItem Is Nothing Then
       StartStaEdit.Value = ""
       Exit Sub
    End If
    
    'verify the station is in right format
    rawStation = CDbl(StartStaEdit.Value)
    If Err Then
        Err.Clear
        rawStation = GetRawStation(StartStaEdit.Value)
        If Err Then
            MsgBox "Please input right format for station."
            rawStation = g_StartStation
        End If
    End If
    
    'verify the startStation >= default value
    If rawStation < GetRoundedStationVal(g_oProfile.StartingStation, g_oProfile.Alignment) Or rawStation > g_EndStation Then
        MsgBox "The StartStation Value is out of range"
        rawStation = g_oProfile.StartingStation
    End If
    g_StartStation = rawStation
    StartStaEdit.Value = g_oProfile.Alignment.GetStationStringWithEquations(rawStation)
End Sub


Private Sub StartStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub

Private Sub StartStaEdit_Change()
    Dim curListItem As ListItem
    Set curListItem = ListView.SelectedItem
    If Not curListItem Is Nothing Then
        curListItem.SubItems(nStationStartIndex) = StartStaEdit.Value
    End If
End Sub

Private Sub EndStaEdit_Exit(ByVal Cancel As MSForms.ReturnBoolean)
    On Error Resume Next
    Dim rawStation As Double
    Dim defaultStation As Double
    Dim curListItem As ListItem
    
    Set curListItem = ListView.SelectedItem
    If g_oProfile Is Nothing Or curListItem Is Nothing Then
       StartStaEdit.Value = ""
       Exit Sub
    End If
    
    'verify the station is in right format
    rawStation = CDbl(EndStaEdit.Value)
    If Err Then
        Err.Clear
        rawStation = GetRawStation(EndStaEdit.Value)
        If Err Then
            MsgBox "Please input right format for station."
            rawStation = g_EndStation
        End If
    End If
    
    'verify the startStation >= default value
    If rawStation > GetRoundedStationVal(g_oProfile.EndingStation, g_oProfile.Alignment) Or rawStation < g_StartStation Then
        MsgBox "The EndStation Value is out of range"
        rawStation = g_oProfile.EndingStation
    End If
    g_EndStation = rawStation
    EndStaEdit.Value = g_oProfile.Alignment.GetStationStringWithEquations(rawStation)
End Sub


Private Sub EndStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub

Private Sub EndStaEdit_Change()
    Dim curListItem As ListItem
    Set curListItem = ListView.SelectedItem
    If Not curListItem Is Nothing Then
        curListItem.SubItems(nStationEndIndex) = EndStaEdit.Value
    End If
End Sub

Private Function GetRoundedStationVal(rawVal As Double, oAlignment As AeccAlignment) As Double
    GetRoundedStationVal = GetRawStation(oAlignment.GetStationStringWithEquations(rawVal))
End Function

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Private g_tlbHeadArr() As String



Option Explicit
' Write the head of html file
Function WriteReportHeader(rptName As String) As Boolean
    Dim str As String
    Dim unitsStr As String
    Dim fs
    Dim ts As TextStream
    
    Set fs = CreateObject("Scripting.FileSystemObject")
    Set ts = fs.CreateTextFile(rptName, True)
 
    str = "<HTML title='PVI Station&Curve Report'><Body>"
    str = str & "<H1>Profile PVI Station & Curve Report</H1>"
   
    ts.WriteLine (str)
    
    'write user's setting
    WriteUserSetting ts
    str = "Date: " & DateTime.Month(DateTime.Date) & "-" & DateTime.Day(DateTime.Date) & "-" & DateTime.Year(DateTime.Date) & "<br/>"
 '   str = str & "Distance Units: " & unitsStr & "<br/><HR/>"
    
    

    ts.WriteLine (str)
    ts.WriteLine ("<HR/>")
    ts.Close

   
    Set fs = Nothing
    Set ts = Nothing
    
    GetTableHead
    
    WriteReportHeader = True
End Function

' Write the end of html file
Function WriteReportFooter(rptName As String) As Boolean
    Dim str As String
    Dim fs, rf, ts
    
  
    Set fs = CreateObject("Scripting.FileSystemObject")
  '  Set rf = fs.GetFile(rptName)
    Set ts = fs.OpenTextFile(rptName, ForAppending)

    str = "</Body></HTML>"
    
    ts.WriteLine (str)
    ts.Close

    Set ts = Nothing
    Set fs = Nothing
    Set rf = Nothing

    WriteReportFooter = True
End Function

' Append one item's report to html file
Function AppendReport(oProfile As AeccProfile, stationStart As Double, stationEnd As Double, rptName As String) As Boolean
    Dim str As String
    Dim fs
    Dim ts As TextStream
    Dim i As Integer


    Set fs = CreateObject("Scripting.FileSystemObject")
 '   Set rf = fs.GetFile(rptName)
    Set ts = fs.OpenTextFile(rptName, ForAppending)

  
    str = "Vertical Alignment: " & oProfile.Name & "<br/>"
    str = str & "Description: " & oProfile.Description & "<br/>"
    str = str & "Station Range: " & "Start: " & oProfile.Alignment.GetStationStringWithEquations(stationStart) _
                & ",  End: " & oProfile.Alignment.GetStationStringWithEquations(stationEnd) & "<br/>"
    ts.WriteLine (str)
'
 

    'extract data
    Call ExtractData(oProfile, stationStart, stationEnd)

    If oProfile.Type = aeccExistingGround Then
        str = "<br><table border='1' width='100%' id='table1'>"
        str = str & "<b><tr><td>" _
              & g_tlbHeadArr(0) & "</td> <td>" _
              & g_tlbHeadArr(1) & "</td> <td>" _
              & g_tlbHeadArr(2) & "</td> </tr></b>"
    
        str = str & "<HR/>"
        ts.WriteLine (str)
        
        For i = 0 To UBound(g_oProfileDataArr)
            If Not TypeName(g_oProfileDataArr(i)) = "Variant()" Then
                Exit For
            End If
                    
                                  
            ts.WriteLine ("<b><tr> <td>" _
                        & CStr(i) & "</td> <td>" _
                        & g_oProfileDataArr(i)(nStationIndex) & "</td> <td>" _
                        & g_oProfileDataArr(i)(nGradeOutIndex) & "</td></tr></b>")

        Next i
    ' Finished Ground Profile
    ElseIf oProfile.Type = aeccFinishedGround Then
        Dim bCurve As Boolean
        str = "<br><table border='1' width='100%' id='table1'>"
        str = str & "<b><tr><td>" _
              & g_tlbHeadArr(0) & "</td> <td>" _
              & g_tlbHeadArr(1) & "</td> <td>" _
              & g_tlbHeadArr(2) & "</td> <td>" _
              & g_tlbHeadArr(3) & "</td> </tr></b>"
    
        str = str & "<HR/>"
        ts.WriteLine (str)
        
        For i = 0 To UBound(g_oProfileDataArr)
            If Not TypeName(g_oProfileDataArr(i)) = "Variant()" Then
                Exit For
            End If
                    
            If TypeName(g_oProfileDataArr(i)(nCurveInfo)) = "Variant()" Then
                bCurve = True
            Else
                bCurve = False
            End If
                   
                  
            
            Dim sCurveLen As String
            If bCurve Then
                sCurveLen = CStr(g_oProfileDataArr(i)(nCurveInfo)(nCurveLenIndex))
            Else
                sCurveLen = "&nbsp;"
            End If
            ts.WriteLine ("<b><tr> <td>" _
                        & CStr(i) & "</td> <td>" _
                        & g_oProfileDataArr(i)(nStationIndex) & "</td> <td>" _
                        & g_oProfileDataArr(i)(nGradeOutIndex) & "</td> <td>" _
                        & sCurveLen & "</td></tr></b>")

            If bCurve Then
                WriteCurveInfoStr i, ts
            End If
        Next i
    End If
    


    ts.WriteLine ("</Table><HR/>")
'    ts.WriteBlankLines (1)
'    ts.WriteBlankLines (1)
'    ts.WriteBlankLines (1)

    ts.Close

    Set ts = Nothing
    Set fs = Nothing
   
'
    AppendReport = True
End Function

Private Sub GetTableHead()
    ReDim g_tlbHeadArr(4)
    g_tlbHeadArr(0) = "PVI"
    g_tlbHeadArr(1) = "Station"
    g_tlbHeadArr(2) = "Grade Out (%)"
    g_tlbHeadArr(3) = "Curve Length"
End Sub


Private Sub WriteCurveInfoStr(nNumber As Integer, ts As TextStream)
'    Public Const nStationIndex = 0
'    Public Const nElevationIndex = 1
'    Public Const nGradeOutIndex = 2
'    Public Const nCurveInfo = 3
'    Public Const nLastIndex = nCurveInfo
'
'    Public Const nCurvTypeIndex = 0
'    Public Const nPVCStationIndex = 1
'    Public Const nPVCElevationIndex = 2
'    Public Const nPVTStationIndex = 3
'    Public Const nPVTElevationIndex = 4
'    Public Const nHighStationIndex = 5
'    Public Const nHightElevation = 6
'    Public Const nLowStationIndex = 7
'    Public Const nLowElevation = 8
'    Public Const nGradeInIndex = 9
'    Public Const nGradeChange = 10
'    Public Const nCurveLenIndex = 11
'    Public Const nKIndex = 12
'    Public Const nHeadlightDisIndex = 13
'    Public Const nPassingDisIndex = 13
'    Public Const nStoppingDisIndex = 14
'    Public Const nLastCurInfoIndex = nStoppingDisIndex

'<DIV style="PADDING-BOTTOM: 4pt; PADDING-TOP: 10pt">Vertical Curve Information: (sag curve)</DIV>
'<TABLE id=ID_CurveTable style="BORDER-TOP: black 1px dashed" cellSpacing=0>
'<TBODY>
'<TR>
'<TD style="PADDING-TOP: 6pt" align=left>PVC Station:</TD>
'<TD style="PADDING-RIGHT: 10pt; PADDING-LEFT: 10pt; PADDING-TOP: 6pt" align=right>0+020</TD>
'<TD style="PADDING-TOP: 6pt" align=left>Elevation:</TD>
'<TD style="PADDING-RIGHT: 10pt; PADDING-LEFT: 10pt; PADDING-TOP: 6pt" align=right>127.40</TD></TR>
'<TR>
'<TD align=left>PVI Station: </TD>
'<TD style="PADDING-RIGHT: 10pt; PADDING-LEFT: 10pt" align=right>0+040</TD>
'<TD align=left>Elevation: </TD>
'<TD style="PADDING-RIGHT: 10pt; PADDING-LEFT: 10pt" align=right>127.05</TD></TR>
'<TR>
'<TD align=left>PVT Station:</TD>
'<TD style="PADDING-RIGHT: 10pt; PADDING-LEFT: 10pt" align=right>0+060</TD>
'<TD align=left>Elevation:</TD>
'<TD style="PADDING-RIGHT: 10pt; PADDING-LEFT: 10pt" align=right>126.91</TD></TR>
'<TR>
'<TD style="PADDING-TOP: 6pt" align=left>Grade in (%): </TD>
'<TD style="PADDING-RIGHT: 10pt; PADDING-LEFT: 10pt; PADDING-TOP: 6pt" align=right>-1.750</TD>
'<TD style="PADDING-TOP: 6pt" align=left>Grade out (%): </TD>
'<TD style="PADDING-RIGHT: 10pt; PADDING-LEFT: 10pt; PADDING-TOP: 6pt" align=right>-0.698</TD></TR>
'<TR>
'<TD align=left>Change (%): </TD>
'<TD style="PADDING-RIGHT: 10pt; PADDING-LEFT: 10pt" align=right>1.052</TD>
'<TD align=left>K: </TD>
'<TD style="PADDING-RIGHT: 10pt; PADDING-LEFT: 10pt" align=right>38.033</TD></TR>
'<TR>
'<TD style="PADDING-TOP: 6pt" align=left>Curve Length: </TD>
'<TD style="PADDING-RIGHT: 10pt; PADDING-LEFT: 10pt; PADDING-TOP: 6pt" align=right>40.000</TD>
'<TD style="PADDING-TOP: 6pt" align=left colSpan=2>&nbsp;</TD></TR>
'<TR>
'<TD align=left>Headlight Distance: </TD>
'<TD style="PADDING-RIGHT: 10pt; PADDING-LEFT: 10pt" align=right>Infinite</TD>
'<TD align=right colSpan=2>&nbsp;</TD></TR></TBODY></TABLE></TD></TR>
    On Error Resume Next
    Dim sType, sValue
    Dim str As String
    Dim oCurveDataArr As Variant
    oCurveDataArr = g_oProfileDataArr(nNumber)(nCurveInfo)
    sType = "<TD style=""PADDING-TOP: 6pt"" align=left>"
    sValue = "<TD style=""PADDING-RIGHT: 10pt; PADDING-LEFT: 10pt; PADDING-TOP: 6pt"" align=right>"
    
    ts.Write ("<TR>")
    ts.Write ("<TD>&nbsp;</TD>")
    ts.Write ("<TD colSpan=4>")
    str = "<DIV style=""PADDING-BOTTOM: 4pt; PADDING-TOP: 10pt"" >Vertical Curve Information:  "
    If oCurveDataArr(nCurvTypeIndex) = aeccSag Then
        str = str & "(sag curve)" & "</DIV>"
    Else
        str = str & "(crest curve)" & "</DIV>"
    End If
    ts.WriteLine (str)
    str = "<TABLE id=ID_CurveTable style=""BORDER-TOP: black 1px dashed"" cellSpacing=0>"
    ts.WriteLine (str)
    ts.WriteLine ("<TBODY>")
        
    'station
    WriteTypeValueRecord2 "PVC Station:", oCurveDataArr(nPVCStationIndex), "Elevation:", oCurveDataArr(nPVCElevationIndex), ts, True
    WriteTypeValueRecord2 "PVI Station:", g_oProfileDataArr(nNumber)(nStationIndex), "Elevation:", g_oProfileDataArr(nNumber)(nElevationIndex), ts
    WriteTypeValueRecord2 "PVT Station:", oCurveDataArr(nPVTStationIndex), "Elevation:", oCurveDataArr(nPVTElevationIndex), ts
    
    If TypeName(oCurveDataArr(nHighStationIndex)) = "String" Then
        WriteTypeValueRecord2 "High Point:", oCurveDataArr(nHighStationIndex), "Elevation:", oCurveDataArr(nHightElevation), ts
    End If
    
    If TypeName(oCurveDataArr(nLowStationIndex)) = "String" Then
        WriteTypeValueRecord2 "Low Point:", oCurveDataArr(nLowStationIndex), "Elevation:", oCurveDataArr(nLowElevation), ts
    End If
    
    WriteTypeValueRecord2 "Grade in(%):", oCurveDataArr(nGradeInIndex), "Grade out(%):", g_oProfileDataArr(nNumber)(nGradeOutIndex), ts, True
    WriteTypeValueRecord2 "Change(%):", oCurveDataArr(nGradeChange), "K:", oCurveDataArr(nKIndex), ts
    
    WriteTypeValueRecord2 "Curve Length:", oCurveDataArr(nCurveLenIndex), "", "", ts, True
    If oCurveDataArr(nCurvTypeIndex) = aeccSag Then
        WriteTypeValueRecord2 "Headlight Distance:", oCurveDataArr(nHeadlightDisIndex), "", "", ts
    Else
        WriteTypeValueRecord2 "Passing Distance:", oCurveDataArr(nPassingDisIndex), "Stopping Distance:", oCurveDataArr(nStoppingDisIndex), ts, True
    End If
    
    str = "</TBODY></TABLE></TD></TR>"
    ts.WriteLine (str)
   
  
    
End Sub
Sub WriteTypeValueRecord2(sType1 As Variant, sValue1 As Variant, sType2 As Variant, sValue2 As Variant, ts As TextStream, Optional bInterval As Boolean = False)
    Dim sTypePrefix, sValuePrefix
    Dim str
    If bInterval = True Then
        sTypePrefix = "<TD style=""PADDING-TOP: 6pt"" align=left>"
    Else
        sTypePrefix = "<TD align=left>"
    End If
    sValuePrefix = "<TD style=""PADDING-RIGHT: 10pt; PADDING-LEFT: 10pt; PADDING-TOP: 6pt"" align=right>"
    
    ts.WriteLine ("<TR>")
    
    str = sTypePrefix & sType1 & "</TD>"
    ts.WriteLine (str)
    str = sValuePrefix & sValue1 & "</TD>"
    ts.WriteLine (str)
    str = sTypePrefix & sType2 & "</TD>"
    ts.WriteLine (str)
    str = sValuePrefix & sValue2 & "</TD>"
    ts.WriteLine (str)
    
    ts.WriteLine ("</TR>")
End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub ProfilePVICurve_RunReport()
    On Error Resume Next
    
    Dim rptDlg As ReportForm_ProfPVICurve
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_ProfPVICurve
    If Err.Number <> 0 Then
        Exit Sub
    End If
    rptDlg.Show

    
    Set rptDlg = Nothing
End Sub
