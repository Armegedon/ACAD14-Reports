Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase


'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strTemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strTemp = strTemp & vbNullChar
    Else
      strTemp = strTemp & strChar
    End If
  Next
  
  ' Put double null at end
  strTemp = strTemp & vbNullChar & vbNullChar
  of.lpstrFilter = strTemp
  
  ' Pad file and file title buffers to maximum path length
  strTemp = m_strFileName & String$(cintMaxFileLength - Len(m_strFileName), 0)
  of.lpstrFile = strTemp
  of.nMaxFile = cintMaxFileLength
  
  strTemp = m_strFileTitle & String$(cintMaxFileLength - Len(m_strFileTitle), 0)
  of.lpstrFileTitle = strTemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Public Const nPointIndex = 0
Public Const nStationIndex = 1
Public Const nOffsetIndex = 2
Public Const nElevation = 3
Public Const nDescriptionRaw = 4
Public Const nDescriptionFull = 5
Public Const nLastIndex = nDescriptionFull

Public g_oPointDataArr(nLastIndex)


Function FormatPtElevationSettings(ByVal dDis As Double) As String
    Dim oElevationSettings As AeccSettingsElevation
    Set oElevationSettings = g_oAeccDb.settings.PointSettings.AmbientSettings.ElevationSettings
        
    FormatPtElevationSettings = FormatDistance(dDis, oElevationSettings.Unit.Value, oElevationSettings.Precision.Value, _
                oElevationSettings.Rounding.Value, oElevationSettings.Sign.Value)
End Function

Function FormatPtCoordSettings(ByVal dDis As Double) As String
    Dim oCoordSettings As AeccSettingsCoordinate
    Set oCoordSettings = g_oAeccDb.settings.PointSettings.AmbientSettings.CoordinateSettings
        
    FormatPtCoordSettings = FormatDistance(dDis, oCoordSettings.Unit.Value, oCoordSettings.Precision.Value, _
                oCoordSettings.Rounding.Value, oCoordSettings.Sign.Value)
End Function

Function FormatDistSettings(ByVal dDis As Double) As String
    Dim oDistSettings As AeccSettingsDistance
    Set oDistSettings = g_oAeccDb.settings.AlignmentSettings.AmbientSettings.DistanceSettings

    FormatDistSettings = FormatDistance(dDis, oDistSettings.Unit.Value, oDistSettings.Precision.Value, _
                oDistSettings.Rounding.Value, oDistSettings.Sign.Value)
End Function

Public Function ExtractData(oAlignment As AeccAlignment, oPoint As AeccPoint) As Boolean
    Dim ptNorthing As Double
    Dim ptEasting As Double
    Dim station As Double
    Dim offSet As Double
    
    ptNorthing = oPoint.Northing
    ptEasting = oPoint.Easting
    
    g_oPointDataArr(nPointIndex) = oPoint.Number
    g_oPointDataArr(nElevation) = FormatDistSettings(oPoint.elevation)
    g_oPointDataArr(nDescriptionRaw) = oPoint.RawDescription
    g_oPointDataArr(nDescriptionFull) = oPoint.FullDescription
    
    If oAlignment.StationOffsetEx(ptEasting, ptNorthing, 0#, station, offSet) = aeccStationOutOfRange Then
        g_oPointDataArr(nStationIndex) = "Out of range"
        g_oPointDataArr(nOffsetIndex) = "Out of range"
    Else
        g_oPointDataArr(nStationIndex) = oAlignment.GetStationStringWithEquations(station)
        g_oPointDataArr(nOffsetIndex) = FormatDistSettings(offSet)
    End If

    ExtractData = True
End Function

Attribute VB_Name = "ReportForm_PointsStaOffset"
Attribute VB_Base = "0{0161E822-BD78-4AA5-AD08-D778912A5CD7}{30B7960D-5163-4A2D-A016-48A66628AAC4}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
'
Private g_AlignsArr()

Private g_sFileName As String
Private g_reportFileName As String

Private g_curAlign As AeccAlignment


Private Const nIncludeIndex = 0
Private Const nPtNumberIndex = 1
Private Const nNorthingIndex = 2
Private Const nEastingIndex = 3
Private Const nElevationIndex = 4
Private Const nNameIndex = 5
Private Const nRawDesriptionIndex = 6
Private Const nFullDescriptionIndex = 7
Private Const nLastIndex = nFullDescriptionIndex

Private sCaptionArr() As String


Private Sub Combo_Align_Change()
    Set g_curAlign = g_AlignsArr(Combo_Align.ListIndex)
    Label_AlignName = g_curAlign.name
    Label_StaRange = "Start:" & g_curAlign.GetStationStringWithEquations(g_curAlign.StartingStation) & "--" _
                      & "End:" & g_curAlign.GetStationStringWithEquations(g_curAlign.EndingStation)
  
    If g_curAlign.StationEquations.Count = 0 Then
        Label_StaEquation = "None"
    Else
        Label_StaEquation = "Applied"
    End If
End Sub



Private Sub DeselAllButton_Click()
    Dim lItem As listItem
    For Each lItem In ListView.ListItems
        lItem.Checked = False
    Next
End Sub



Private Sub HelpButton_Click()
    ReportsHH_hWnd = ReportsHtmlHelp(0, getReportsHelpFile, HH_HELP_CONTEXT, IDH_AECC_REPORTS_CREATE_STATION_OFFSET_TO_POINTS_REPORT)
End Sub

Private Sub SelAlignButton_Click()
    On Error GoTo Cancel
    Dim oEntity As Object
    Dim pt(2) As Double
    Me.Hide
    ThisDrawing.Utility.GetEntity oEntity, pt, "Select a Alignment."
    Do While Not TypeOf oEntity Is AeccAlignment
        ThisDrawing.Utility.GetEntity oEntity, pt, "Please select a Alignment."
    Loop
    Combo_Align.Text = oEntity.name
Cancel:
    Me.Show
End Sub

Private Sub SelAllButton_Click()
    Dim lItem As listItem
    For Each lItem In ListView.ListItems
        lItem.Checked = True
    Next
End Sub

' Initialize the main dialog
Private Sub UserForm_Initialize()
    Dim tempPath As String
    Dim oSite As AeccSite
    Dim oAlign As AeccAlignment
    Dim nAlignCount As Long
    Dim nCurAlignIndex As Long
    
    If g_oAeccDb.Points.Count = 0 Then
        MsgBox "No points in " & ThisDrawing.name & " exist."
        End
    End If
    
    
    g_sFileName = g_oCivilApp.Path

    tempPath = Environ("temp")
    g_reportFileName = tempPath & "\civilreport.html"


' init controls
    ReportFileNameEdit.Text = g_reportFileName

    ' progress bar settings
    ProgressBar.Min = 0
    ProgressBar.Max = 100
    ProgressBar.Visible = False
    progressBarLabel.Visible = False


    
    
    ' Get Captions
    GetCaptions
    
    ' list view grid setup
    ' setup columns
    Call ListView.ColumnHeaders.Add(, , sCaptionArr(nIncludeIndex), 40, lvwColumnLeft)
    Call ListView.ColumnHeaders.Add(, , sCaptionArr(nPtNumberIndex), 80, lvwColumnLeft)
    Call ListView.ColumnHeaders.Add(, , sCaptionArr(nNorthingIndex), 60, lvwColumnLeft)
    Call ListView.ColumnHeaders.Add(, , sCaptionArr(nEastingIndex), 60, lvwColumnLeft)
    Call ListView.ColumnHeaders.Add(, , sCaptionArr(nElevationIndex), 80, lvwColumnLeft)
    Call ListView.ColumnHeaders.Add(, , sCaptionArr(nNameIndex), 40, lvwColumnLeft)
    Call ListView.ColumnHeaders.Add(, , sCaptionArr(nRawDesriptionIndex), 100, lvwColumnLeft)
    Call ListView.ColumnHeaders.Add(, , sCaptionArr(nFullDescriptionIndex), 100, lvwColumnLeft)
    
    

    FillGrid

    
    'Alignments
    nAlignCount = 0
    nCurAlignIndex = 0
    
    
    nAlignCount = g_oAeccDoc.AlignmentsSiteless.Count
    If nAlignCount > 0 Then
        ReDim Preserve g_AlignsArr(nAlignCount - 1)
    End If
    For Each oAlign In g_oAeccDoc.AlignmentsSiteless
        Set g_AlignsArr(nCurAlignIndex) = oAlign
        Combo_Align.AddItem (oAlign.name)
        nCurAlignIndex = nCurAlignIndex + 1
    Next

    
    For Each oSite In g_oAeccDb.Sites
        nAlignCount = oSite.Alignments.Count + nAlignCount
        If nAlignCount > 0 Then
            ReDim Preserve g_AlignsArr(nAlignCount - 1)
        End If
        For Each oAlign In oSite.Alignments
            Set g_AlignsArr(nCurAlignIndex) = oAlign
            Combo_Align.AddItem (oAlign.name)
            nCurAlignIndex = nCurAlignIndex + 1
        Next
    Next
    If nAlignCount > 0 Then
        Combo_Align.ListIndex = 0
    Else
        MsgBox "No alignments in " & ThisDrawing.name & " exist."
        End
    End If

End Sub


' Do the real work of gnerating the report here
Private Sub ExecuteButton_Click()
    Dim t, cCount As Integer
    Dim pbarInc As Single
    Dim oPoint As AeccPoint
    Dim curListItem As listItem
    Dim exeStr As String
    

    If ListView.ListItems.Count = 0 Then
        Exit Sub
    End If

    For t = 1 To ListView.ListItems.Count
        If ListView.ListItems(t).Checked = True Then
            cCount = cCount + 1
        End If
    Next
'
    If cCount = 0 Then
        MsgBox "Please select at least one Point."
        Exit Sub
    End If
    pbarInc = 90 / cCount
'
    progressBarLabel.Enabled = False
    progressBarLabel.Enabled = True

    progressBarLabel.Visible = True
    ProgressBar.Visible = True
'
        'update progress bar
    ProgressBar.Value = 0
    
    Call WriteReportHeader(g_curAlign, g_reportFileName)
'
    For t = 1 To ListView.ListItems.Count
        Set curListItem = ListView.ListItems(t)
        If curListItem.Checked = True Then
            Set oPoint = g_oAeccDb.Points.Find(curListItem.SubItems(nPtNumberIndex))
            If Not oPoint Is Nothing Then
                Call AppendReport(g_curAlign, oPoint, g_reportFileName)
                ProgressBar.Value = ProgressBar.Value + pbarInc
            End If
        End If
    Next
'
    'update progress bar
    ProgressBar.Value = 100

    ProgressBar.Visible = False
    progressBarLabel.Visible = False


    Call WriteReportFooter(g_reportFileName)

    OpenFileByDefaultBrowser g_reportFileName

End Sub

Private Sub CancelButton_Click()

    Unload Me

End Sub

Private Sub UserForm_Terminate()

    ' clean up created objects
    Set g_oCivilApp = Nothing
    Set g_oAeccDoc = Nothing
    Set g_oAeccDb = Nothing
    Set g_curAlign = Nothing
End Sub

Private Sub FileSelectionButton_Click()

    Dim fileDialog As New CFileDialog
    
    With fileDialog

        .DefaultExt = "html"

        .DialogTitle = "Select a HTML File"

        .Filter = "HTML Files|*.HTML"

        .FilterIndex = 1

        .MaxFileSize = 255

        .FileName = g_reportFileName

        If .Show(True) Then

            g_reportFileName = fileDialog.FileName
            ReportFileNameEdit.Text = g_reportFileName

        Else

            Exit Sub

        End If

    End With

End Sub

' Fill the data to Grid
Private Sub FillGrid()
    Dim oPoints As AeccPoints
    Dim oPoint As AeccPoint
    Dim li As listItem
    For Each oPoint In g_oAeccDb.Points
        Set li = ListView.ListItems.Add
        li.SubItems(nPtNumberIndex) = oPoint.Number
        li.SubItems(nNorthingIndex) = FormatPtCoordSettings(oPoint.Northing)
        li.SubItems(nEastingIndex) = FormatPtCoordSettings(oPoint.Easting)
        li.SubItems(nElevationIndex) = FormatPtElevationSettings(oPoint.elevation)
        On Error Resume Next
        Dim name As String
        name = ""
        name = oPoint.name
        On Error GoTo 0
        li.SubItems(nNameIndex) = name
        li.SubItems(nRawDesriptionIndex) = oPoint.RawDescription
        li.SubItems(nFullDescriptionIndex) = oPoint.FullDescription
        li.Checked = True
    Next


End Sub


Private Sub GetCaptions()
    ReDim sCaptionArr(nLastIndex)
    sCaptionArr(nIncludeIndex) = "Include"
    sCaptionArr(nPtNumberIndex) = "Point Number"
    sCaptionArr(nNorthingIndex) = "Northing"
    sCaptionArr(nEastingIndex) = "Easting"
    sCaptionArr(nElevationIndex) = "Point Elevation"
    sCaptionArr(nNameIndex) = "Name"
    sCaptionArr(nRawDesriptionIndex) = "Raw Description"
    sCaptionArr(nFullDescriptionIndex) = "Full Description"
End Sub

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Private g_tlbHeadArr() As String

Option Explicit
Function WriteReportHeader(oAlignment As AeccAlignment, rptName As String) As Boolean
    Dim str As String
    Dim unitsStr As String
    Dim fs
    Dim ts As TextStream
    
    'unitsStr = GetUnitStr
 
    Set fs = CreateObject("Scripting.FileSystemObject")
    Set ts = fs.CreateTextFile(rptName, ForWriting, True)
    
    
    str = "<HTML title='Station Offset to Points Report'><Body>"
    ts.WriteLine (str)
    ts.WriteLine ("<Body>")
    ts.WriteLine ("<center>")
    
    str = "<H1>Station Offset to Points Report</H1>"
    ts.WriteLine (str)
    ts.WriteLine ("</center>")
    
      
    
    ' write owner and client setting
    WriteUserSetting ts
    
    ts.WriteLine ("<HR/>")
    
    ' data info
    str = "Date: " & DateTime.Month(DateTime.Date) & "-" & DateTime.Day(DateTime.Date) & "-" & DateTime.Year(DateTime.Date) & "<br/>"
    ts.WriteLine (str)
    
    ts.WriteLine ("<HR/>")
    
        ' alignment info
    str = "Alignment Name: " & oAlignment.name & "<br/>"
    str = str & "Description: " & oAlignment.description & "<br/>"
    str = str & "Station Range: " & "Start: " & oAlignment.GetStationStringWithEquations(oAlignment.StartingStation) _
                & ",  End: " & oAlignment.GetStationStringWithEquations(oAlignment.EndingStation) & "<br/>"
    
    ts.Write (str)
    
    GetTableHead
    
    str = "<br><table border='1' width='100%' id='table1'>"
    str = str & "<b><tr><td>" _
          & g_tlbHeadArr(0) & "</td> <td>" _
          & g_tlbHeadArr(1) & "</td> <td>" _
          & g_tlbHeadArr(2) & "</td> <td>" _
          & g_tlbHeadArr(3) & "</td> <td>" _
          & g_tlbHeadArr(4) & "</td> </tr></b>"
    ts.WriteLine (str)
    
    ts.Close

   
    Set fs = Nothing
    Set ts = Nothing
    
   
    
    WriteReportHeader = True
End Function

' Write the end of html file
Function WriteReportFooter(rptName As String) As Boolean
    Dim str As String
    Dim fs, rf, ts
    
  
    Set fs = CreateObject("Scripting.FileSystemObject")
    Set rf = fs.GetFile(rptName)
    Set ts = rf.OpenAsTextStream(ForAppending, TristateUseDefault)

    str = "</Body></HTML>"
    
    ts.WriteLine (str)
    
  
    
    ts.Write ("</Table><HR/>")
    ts.WriteLine ("Out of Range: The Point is not adjacent to alignment.</br>")
    ts.Close

    Set ts = Nothing
    Set fs = Nothing
    Set rf = Nothing

    WriteReportFooter = True
End Function

' Append one item's report to html file
Function AppendReport(oAlignment As AeccAlignment, oPoint As AeccPoint, rptName As String) As Boolean
    Dim str As String
    Dim fs, rf, ts
    Dim i As Integer
   
    
    Set fs = CreateObject("Scripting.FileSystemObject")
    Set rf = fs.GetFile(rptName)
    Set ts = rf.OpenAsTextStream(ForAppending, TristateUseDefault)

   ' extract data
    Call ExtractData(oAlignment, oPoint)
    
    Dim description As String
    If Not g_oPointDataArr(nDescriptionRaw) = "" Then
        description = "(" + g_oPointDataArr(nDescriptionRaw) + ")"
    End If
    description = description + g_oPointDataArr(nDescriptionFull)
    If description = "" Then
        description = "&nbsp"
    End If
    ts.Write ("<b><tr> <td>" _
                & g_oPointDataArr(nPointIndex) & "</td> <td>" _
                & g_oPointDataArr(nStationIndex) & "</td> <td>" _
                & g_oPointDataArr(nOffsetIndex) & "</td> <td>" _
                & g_oPointDataArr(nElevation) & "</td> <td>" _
                & description _
                & "</td></tr></b>")

    ts.Close

    Set ts = Nothing
    Set fs = Nothing
    Set rf = Nothing
    
    AppendReport = True
End Function

Private Sub GetTableHead()
    ReDim g_tlbHeadArr(4)
    g_tlbHeadArr(0) = "Point"
    g_tlbHeadArr(1) = "Station"
    g_tlbHeadArr(2) = "Offset"
    g_tlbHeadArr(3) = "Elevation"
    g_tlbHeadArr(4) = "Description"
End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub PointsStaOffset_RunReport()
    On Error Resume Next
    
    Dim rptDlg As ReportForm_PointsStaOffset
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_PointsStaOffset
    If Err.Number <> 0 Then
        Exit Sub
    End If
    rptDlg.Show
    
    Set rptDlg = Nothing
End Sub
