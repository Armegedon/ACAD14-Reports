Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDoc As AeccDocument
Public g_oAeccDb As AeccDatabase


'
' Start Civil 3D, create document and database objects.
'
Public Function InitCivil3D() As Boolean
    Dim oApp As AcadApplication
    Set oApp = ThisDrawing.Application
    Const sAppName = "AeccXUiLand.AeccApplication." + MODVER
    Set g_oCivilApp = oApp.GetInterfaceObject(sAppName)
    If g_oCivilApp Is Nothing Then
        MsgBox "Error creating " & sAppName & ", exit."
        InitCivil3D = False
        Exit Function
    End If
    Set g_oAeccDoc = g_oCivilApp.ActiveDocument
    Set g_oAeccDb = g_oAeccDoc.Database
   
    InitCivil3D = True
End Function

Attribute VB_Name = "CAlignmentPIs"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit


Private mObject As AeccAlignment
Private mPIs As New Dictionary



Private Sub Class_Initialize()
    Set mObject = Nothing
End Sub

Public Property Get Alignment() As AeccAlignment
  Set Alignment = mObject
End Property

Public Property Let Alignment(oAlignment As AeccAlignment)
  Set mObject = oAlignment
  If Not oAlignment Is Nothing Then
    mPIs.removeAll
    Dim lCount As Long
    Dim oStation As AeccAlignmentStation
    lCount = 0
    For Each oStation In oAlignment.GetStations(aeccGeometryPoint, 0#, 0#)
        lCount = lCount + 1
        mPIs.Add lCount, oStation.Station
    Next
  End If
End Property

Public Property Get PICounts() As Long
    PICounts = mPIs.Count
End Property

Public Function GetStationByNum(ByVal num As Long) As Double
    Dim lRes As Double
    
    If mPIs.Exists(num) Then
        lRes = mPIs.item(num)
    End If
    GetStationByNum = lRes
End Function

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strtemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strtemp = strtemp & vbNullChar
    Else
      strtemp = strtemp & strChar
    End If
  Next
  
  ' Put double null at end
  strtemp = strtemp & vbNullChar & vbNullChar
  of.lpstrFilter = strtemp
  
  ' Pad file and file title buffers to maximum path length
  strtemp = m_strFileName & String$(cintMaxFileLength - Len(m_strFileName), 0)
  of.lpstrFile = strtemp
  of.nMaxFile = cintMaxFileLength
  
  strtemp = m_strFileTitle & String$(cintMaxFileLength - Len(m_strFileTitle), 0)
  of.lpstrFileTitle = strtemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "CReachRegion"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Private mBeginPt As Long
Private mEndPt As Long


Public Property Get BeginPt() As Long
    BeginPt = mBeginPt
End Property

Public Property Get EndPt() As Long
    EndPt = mEndPt
End Property

Public Function SetValue(ByVal dBeginPt As Long, ByVal dEndPt As Long) As Boolean
    If (Not dBeginPt = dEndPt) And dBeginPt >= 1# Then
        mBeginPt = dBeginPt
        mEndPt = dEndPt
        SetValue = True
    Else
        SetValue = False
    End If
End Function

Attribute VB_Name = "CSTEAM"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Dim mSampleLineGroup As AeccSampleLineGroup
Public mReaches As New Dictionary 'key is reaches name, value is the begin and End Position

Public Function AddReach(sReachName As String, lBegin As Long, lEnd As Long) As Boolean
    Dim bRes As Boolean
    bRes = False
    If Not mReaches.Exists(sReachName) Then
        Dim oReach As New CReachRegion
        If oReach.SetValue(lBegin, lEnd) Then
            mReaches.Add sReachName, oReach
            bRes = True
        End If
    End If
    AddReach = bRes
End Function

Public Function RemoveReach(sReachName As String) As Boolean
    Dim bRes As Boolean
    bRes = False
    If mReaches.Exists(sReachName) Then
       mReaches.Remove sReachName
       bRes = True
       
    End If
    RemoveReach = bRes
End Function

Public Property Let SampleLineGroup(oSampleLineGroup As AeccSampleLineGroup)
    Set mSampleLineGroup = oSampleLineGroup
    mReaches.removeAll
End Property


Public Property Get SampleLineGroup() As AeccSampleLineGroup
    Set SampleLineGroup = mSampleLineGroup
End Property

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit


Public Const nEasting = 0
Public Const nNorthing = 1
Public Const nElevation = 2
Public Const nID = 3
Public Const nStation = 3

Public g_Alignments As New Dictionary


Function FormatCoordSettings(ByVal dDis As Double) As String
    Dim oCoordSettings As AeccSettingsCoordinate
    Set oCoordSettings = g_oAeccDb.Settings.AlignmentSettings.AmbientSettings.CoordinateSettings

    FormatCoordSettings = FormatDistance(dDis, oCoordSettings.Unit.Value, oCoordSettings.Precision.Value, _
                oCoordSettings.Rounding.Value, oCoordSettings.Sign.Value, False)
End Function
'
'
Public Function ExtractData(oSteam As CSTEAM) As Boolean
    On Error Resume Next
    g_oDataToReport.Clear
    

    
    'Get Stream EndPts
    Dim sAlignmentName As String
    Dim arrEndPt(3) As String
    Dim oAlignmentPIs As CAlignmentPIs
    Dim oAlignment As AeccAlignment
    Dim i As Long
    Dim dStation As Double
    Dim dNorthing As Double
    Dim dEasting As Double
    Dim dElevation As Double
    
    sAlignmentName = oSteam.SampleLineGroup.Parent.Name
    Set oAlignmentPIs = g_Alignments.item(sAlignmentName)
    Set oAlignment = oAlignmentPIs.Alignment
    For i = 1 To oAlignmentPIs.PICounts Step 1
        dStation = oAlignmentPIs.GetStationByNum(i)
        oAlignment.PointLocation dStation, 0#, dEasting, dNorthing
        arrEndPt(nEasting) = FormatCoordSettings(dEasting)
        arrEndPt(nNorthing) = FormatCoordSettings(dNorthing)
        Dim oSurface As AeccSurface
        Set oSurface = GetSampledSurface(oSteam.SampleLineGroup)
        arrEndPt(nElevation) = FormatCoordSettings(oSurface.FindElevationAtXY(dEasting, dNorthing))
        arrEndPt(nID) = CStr(i)
        g_oDataToReport.EndPoints.Add arrEndPt
    Next
    
    'Get Reaches
    GetReachesData oSteam
    
    'Get CrossSections
    GetSectionsData oSteam
    ExtractData = True
    
    ' Get Header Data
    GetHeaderData oSteam

End Function
'
Public Sub GetHeaderData(oSteam As CSTEAM)
    Dim oHeader As DataHeader
    Dim oSampleLineGroup As AeccSampleLineGroup
    Dim oSurface As AeccSurface
    Set oSampleLineGroup = oSteam.SampleLineGroup
    Set oHeader = g_oDataToReport.header
    
    'get Units:
    Dim disOriUnit As AeccDrawingUnitType
    disOriUnit = g_oAeccDb.Settings.DrawingSettings.UnitZoneSettings.DrawingUnits
    If disOriUnit = aeccDrawingUnitFeet Then
        oHeader.Units = "ENGLISH"
    Else
        oHeader.Units = "METRIC"
    End If
    
    'get DTM TYPE:
    Set oSurface = GetSampledSurface(oSteam.SampleLineGroup)
    oHeader.DTM = oSurface.Name
    Select Case oSurface.Type
    Case aecckGridSurface
        oHeader.DTMType = "GRID"
    Case aecckGridVolumeSurface
        oHeader.DTMType = "GRIDVOLUME"
    Case aecckTinSurface
        oHeader.DTMType = "TIN"
    Case Else
        oHeader.DTMType = "TINVOLUME"
    End Select
    
    'get Number of Reaches;
    oHeader.NumberOfReaches = g_oDataToReport.Reaches.Count
    
    'get Number of Sections
    oHeader.NumberOfCrossSection = g_oDataToReport.CrossSections.Count
    
    'get MAP Projections:
    oHeader.MapProjection = g_oAeccDb.Settings.DrawingSettings.UnitZoneSettings.CoordinateSystem.Projection
    
    'get Datum:
    oHeader.Datum = g_oAeccDb.Settings.DrawingSettings.UnitZoneSettings.CoordinateSystem.Datum
    
    
End Sub

Public Sub GetReachesData(oSteam As CSTEAM)
    Dim sAlignmentName As String
    Dim oAlignmentPIs As CAlignmentPIs
    Dim oAlignment As AeccAlignment
    Dim dicReaches As Dictionary
    Dim oReachData As DataReach
    Dim oReachRegion As CReachRegion
    Dim sReachName As String
    Dim i As Long
    
    sAlignmentName = oSteam.SampleLineGroup.Parent.Name
    Set oAlignmentPIs = g_Alignments.item(sAlignmentName)
    Set oAlignment = oAlignmentPIs.Alignment
    
    Set dicReaches = oSteam.mReaches
    For i = 0 To dicReaches.Count - 1 Step 1
        sReachName = dicReaches.Keys(i)
        Set oReachRegion = dicReaches.item(sReachName)
        Set oReachData = New DataReach
        oReachData.SteamID = oSteam.SampleLineGroup.Parent.Name
        oReachData.ReachID = sReachName
        oReachData.FromPoint = CStr(oReachRegion.BeginPt)
        oReachData.ToPoint = CStr(oReachRegion.EndPt)
        
        Dim j As Long
        Dim arrEndPt(3) As String
        Dim dStation As Double, dEasting As Double, dNorthing As Double
        Dim dStep As Long
        If oReachRegion.BeginPt < oReachRegion.EndPt Then
            dStep = 1
        Else
            dStep = -1
        End If
        For j = oReachRegion.BeginPt To oReachRegion.EndPt Step dStep
            dStation = oAlignmentPIs.GetStationByNum(j)
            oAlignment.PointLocation dStation, 0#, dEasting, dNorthing
            arrEndPt(nEasting) = FormatCoordSettings(dEasting)
            arrEndPt(nNorthing) = FormatCoordSettings(dNorthing)
            Dim oSurface As AeccSurface
            Set oSurface = GetSampledSurface(oSteam.SampleLineGroup)
            arrEndPt(nElevation) = FormatCoordSettings(oSurface.FindElevationAtXY(dEasting, dNorthing))
            arrEndPt(nStation) = oAlignment.GetStationStringWithEquations(dStation)
            oReachData.EndPoints.Add arrEndPt
        Next j
        g_oDataToReport.Reaches.Add oReachData
    Next i
End Sub

Public Sub GetSectionsData(oSteam As CSTEAM)
    Dim oSampleLine As AeccSampleLine
    Dim oReachRegion As CReachRegion
    Dim oAlignmentPIs As CAlignmentPIs
    Dim oDataSection As DataSection
    Dim sReachName As String
    Dim dBeginStation As Double
    Dim dEndStation As Double
    Dim i As Long
    Dim tmpCol As New Collection
    
    Set oAlignmentPIs = g_Alignments.item(oSteam.SampleLineGroup.Parent.Name)
    For i = 0 To oSteam.mReaches.Count - 1 Step 1
        sReachName = oSteam.mReaches.Keys(i)
        Set oReachRegion = oSteam.mReaches.item(sReachName)
        dBeginStation = oAlignmentPIs.GetStationByNum(oReachRegion.BeginPt)
        dEndStation = oAlignmentPIs.GetStationByNum(oReachRegion.EndPt)
            
        For Each oSampleLine In oSteam.SampleLineGroup.SampleLines
            Dim dStation As Double
            dStation = oSampleLine.Station
            If (dStation >= dBeginStation And dStation <= dEndStation) Or (dStation <= dBeginStation And dStation >= dEndStation) Then
                Set oDataSection = New DataSection
                oDataSection.SteamID = oSteam.SampleLineGroup.Parent.Name
                oDataSection.ReachID = sReachName
                oDataSection.Station = oSteam.SampleLineGroup.Parent.GetStationStringWithEquations(dStation)
                
                'sort the vertexs
                Dim vertexs As AeccSampleLineVertices
                Dim oVertex As AeccSampleLineVertex
                Set tmpCol = New Collection
                Dim k As Integer
                Dim j As Integer
                Dim tmpVer1 As AeccSampleLineVertex
                Dim tmpVer2 As AeccSampleLineVertex
                Set vertexs = oSampleLine.Vertices
                tmpCol.Add vertexs.item(0)
                For k = 1 To (vertexs.Count - 1)
                    Set tmpVer1 = vertexs.item(k)
                    For j = 1 To tmpCol.Count
                        Set tmpVer2 = tmpCol.item(j)
                        If tmpVer1.StationOffset < tmpVer2.StationOffset Then
                            Exit For
                        End If
                        
                    Next j
                    If j > tmpCol.Count Then
                        tmpCol.Add item:=tmpVer1, after:=tmpCol.Count
                    Else
                        tmpCol.Add item:=tmpVer1, before:=j
                    End If
                    
                Next k
                '
                ' Add to oDataSection.CutLines
                Dim location(1) As String
                
                For k = 0 To vertexs.CountLeft - 1
                    Set oVertex = tmpCol.item(k + 1)
                    location(nEasting) = FormatCoordSettings(oVertex.location(0))
                    location(nNorthing) = FormatCoordSettings(oVertex.location(1))
                    oDataSection.CutLines.Add location
                Next k
                
                Dim dEasting As Double
                Dim dNorthing As Double
                oSteam.SampleLineGroup.Parent.PointLocation dStation, 0#, dEasting, dNorthing
                location(nEasting) = FormatCoordSettings(dEasting)
                location(nNorthing) = FormatCoordSettings(dNorthing)
                oDataSection.CutLines.Add location
                
                For k = 0 To vertexs.CountRight - 1
                    Set oVertex = tmpCol.item(vertexs.CountLeft + k + 1)
                    location(nEasting) = FormatCoordSettings(oVertex.location(0))
                    location(nNorthing) = FormatCoordSettings(oVertex.location(1))
                    oDataSection.CutLines.Add location
                Next k
                
                
                g_oDataToReport.CrossSections.Add oDataSection
            End If
        Next
        
    Next i
End Sub

Public Function GetSampledSurface(oSampleLineGroup As AeccSampleLineGroup) As AeccSurface
    Set GetSampledSurface = Nothing
    Dim oSampledSurface As AeccSampledSurface
    Dim i As Long
    Dim bFound As Boolean
    bFound = False
    i = 0
    Do While (bFound = False And i < oSampleLineGroup.SampledSurfaces.Count)
        Dim oSurface As AeccSurface
        Set oSurface = oSampleLineGroup.SampledSurfaces.item(i).Surface
        If oSurface.Type = aecckTinSurface Then
            Set GetSampledSurface = oSurface
            bFound = True
        End If
        i = i + 1
    Loop
End Function

Attribute VB_Name = "DataHeader"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit


 Public Units As String
 Public DTMType As String
 Public DTM As String
 Public NumberOfReaches
 Public NumberOfCrossSection
 Public MapProjection As String
 Public Datum As String

Attribute VB_Name = "DataReach"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public SteamID As String
Public ReachID As String
Public FromPoint As Long
Public ToPoint As Long

Public EndPoints As New Collection

Attribute VB_Name = "DataSection"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public SteamID As String
Public ReachID As String
Public Station As String


Public CutLines As New Collection

Attribute VB_Name = "DataSteamNetwork"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Option Explicit

Public header As New DataHeader
Public EndPoints As New Collection
Public Reaches As New Collection
Public CrossSections As New Collection

Public Sub Clear()
    Set EndPoints = New Collection
    Set Reaches = New Collection
    Set CrossSections = New Collection
End Sub

Attribute VB_Name = "ReportForm_HECRAS"
Attribute VB_Base = "0{BAF279F8-BA19-4DD3-B343-D97FA13B0B44}{CD045E0E-DFA9-4792-8BD3-DC4FA1F8DE0F}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
'

Private g_sFileName As String
Private g_reportFileName As String


Private g_Steams As New Dictionary

Private Const nNameIndex = 0
Private Const nBeginPtIndex = 1
Private Const nEndPtIndex = 2
Private Const nLastIndex = nEndPtIndex

Private sCaptionArr() As String


Private Sub DeleteButton_Click()

    Dim i As Long
    Dim item As ListItem
    Dim colItems As ListItems
    Dim oSteam As CSTEAM
    
    If Not g_Steams.Exists(Combo_LineGroup.Text) Then
        Exit Sub
    End If
    Set oSteam = g_Steams.item(Combo_LineGroup.Text)
    
    Set colItems = ListView.ListItems
    For i = 1 To colItems.Count Step 1
        Set item = colItems.item(i)
        If item.Selected = True Then
            Call oSteam.RemoveReach(item.Text)
            colItems.Remove i
            i = i - 1
        End If
        If i = colItems.Count Then
            Exit For
        End If
    Next i
    If ListView.ListItems.Count = 0 Then
        DeleteButton.Visible = False
    End If

End Sub
Private Sub AddButton_Click()
    Dim oSteam As CSTEAM
    Dim lBeginPtNum As Long
    Dim lEndPtNum As Long
    
    If Not g_Steams.Exists(Combo_LineGroup.Text) Then
        Exit Sub
    End If
    Set oSteam = g_Steams.item(Combo_LineGroup.Text)
    lBeginPtNum = Combo_BeginPt.ListIndex + 1
    lEndPtNum = Combo_EndPt.ListIndex + 1
    
    If oSteam.AddReach(TextBox_Name.Text, lBeginPtNum, lEndPtNum) Then
        Dim item As ListItem
        Set item = ListView.ListItems.Add(, , TextBox_Name.Text)
        item.SubItems(nBeginPtIndex) = Combo_BeginPt.Text
        item.SubItems(nEndPtIndex) = Combo_EndPt.Text
        DeleteButton.Visible = True
    Else
        MsgBox "The Reach's name is existing or the Begin and End Point input error."
    End If
    
End Sub

Private Sub Combo_LineGroup_Change()
    TextBox_Name.Text = ""
    Dim oSteam As CSTEAM
    Dim lBeginPtNum As Long
    Dim lEndPtNum As Long
    Dim dicReaches As Dictionary
    Dim oAlignment As AeccAlignment
    Dim sReachName As String
    Dim oReachRegion As CReachRegion
    Dim i As Long
        
    If Not g_Steams.Exists(Combo_LineGroup.Text) Then
        Exit Sub
    End If
    Set oSteam = g_Steams.item(Combo_LineGroup.Text)
    Set dicReaches = oSteam.mReaches
    Set oAlignment = oSteam.SampleLineGroup.Parent
    
    ListView.ListItems.Clear
    For i = 0 To dicReaches.Count - 1 Step 1
        Dim item As ListItem
        sReachName = dicReaches.Keys(i)
        Set oReachRegion = dicReaches.item(sReachName)
        Set item = ListView.ListItems.Add(, , sReachName)
        item.SubItems(nBeginPtIndex) = oAlignment.GetStationStringWithEquations(oReachRegion.BeginPt)
        item.SubItems(nEndPtIndex) = oAlignment.GetStationStringWithEquations(oReachRegion.EndPt)
    Next i
    
End Sub

Private Sub Combo_Align_Change()
    Dim oAlignment As AeccAlignment
    Dim oSampleLineGroup As AeccSampleLineGroup
    Dim Station As AeccAlignmentStation
    Dim oAlignmentPIs As CAlignmentPIs
    Dim i As Long
    
    Set oAlignment = g_Alignments.item(Combo_Align.SelText).Alignment
    Combo_LineGroup.Clear
    
    For Each oSampleLineGroup In oAlignment.SampleLineGroups
        Combo_LineGroup.AddItem oSampleLineGroup.Name
    Next
    
    If Combo_LineGroup.ListCount > 0 Then
        Combo_LineGroup.ListIndex = 0
    End If
    
    Combo_BeginPt.Clear
    Combo_EndPt.Clear

    Set oAlignmentPIs = g_Alignments.item(Combo_Align.Text)
    For i = 1 To oAlignmentPIs.PICounts Step 1
        Combo_BeginPt.AddItem oAlignment.GetStationStringWithEquations(oAlignmentPIs.GetStationByNum(i))
        Combo_EndPt.AddItem oAlignment.GetStationStringWithEquations(oAlignmentPIs.GetStationByNum(i))
    Next
    ' Initial Reach begin and end points list box
    
    If Combo_BeginPt.ListCount > 0 Then
        Combo_BeginPt.ListIndex = 0
    End If
    If Combo_EndPt.ListCount > 0 Then
        Combo_EndPt.ListIndex = Combo_EndPt.ListCount - 1
    End If
End Sub



Private Sub HelpButton_Click()
    ReportsHH_hWnd = ReportsHtmlHelp(0, getReportsHelpFile, HH_HELP_CONTEXT, IDH_AECC_REPORTS_CREATE_HEC_RAS_REPORT)
End Sub

Private Sub TextBox_Name_Change()
    If TextBox_Name.Text <> "" Then
        Combo_BeginPt.Enabled = True
        Combo_EndPt.Enabled = True
        AddButton.Enabled = True
    Else
        Combo_BeginPt.Enabled = False
        Combo_EndPt.Enabled = False
        AddButton.Enabled = False
    End If
End Sub

' Initialize the main dialog
Private Sub UserForm_Initialize()
    Dim tempPath As String
    Dim oSite As AeccSite
    Dim oAlignment As AeccAlignment
    Dim oAlignmentPIs As CAlignmentPIs
    Dim oSteam As CSTEAM
    Dim oSampleLineGroup As AeccSampleLineGroup
   
    g_sFileName = g_oCivilApp.Path

    tempPath = Environ("temp")
    g_reportFileName = tempPath & "\HEC-RAS.geo"


    ReportFileNameEdit.Text = g_reportFileName

    'initial Select report Components
    g_Alignments.removeAll
    g_Steams.removeAll
    
    ' siteless alignment
    For Each oAlignment In g_oAeccDoc.AlignmentsSiteless
        If oAlignment.SampleLineGroups.Count > 0 Then
            If g_Alignments.Exists(oAlignment.Name) = False Then
                Set oAlignmentPIs = New CAlignmentPIs
                oAlignmentPIs.Alignment = oAlignment
                g_Alignments.Add oAlignment.Name, oAlignmentPIs
                Combo_Align.AddItem oAlignment.Name
                For Each oSampleLineGroup In oAlignment.SampleLineGroups
                    Set oSteam = New CSTEAM
                    oSteam.SampleLineGroup = oSampleLineGroup
                    g_Steams.Add oSampleLineGroup.Name, oSteam
                Next
            End If
        End If
    Next
    
    'alignment from sites
    For Each oSite In g_oAeccDb.Sites
        For Each oAlignment In oSite.Alignments
            If oAlignment.SampleLineGroups.Count > 0 Then
                If g_Alignments.Exists(oAlignment.Name) = False Then
                    Set oAlignmentPIs = New CAlignmentPIs
                    oAlignmentPIs.Alignment = oAlignment
                    g_Alignments.Add oAlignment.Name, oAlignmentPIs
                    Combo_Align.AddItem oAlignment.Name
                    For Each oSampleLineGroup In oAlignment.SampleLineGroups
                        Set oSteam = New CSTEAM
                        oSteam.SampleLineGroup = oSampleLineGroup
                        g_Steams.Add oSampleLineGroup.Name, oSteam
                    Next
                End If
            End If
        Next
    Next
    
    If g_Alignments.Count > 0 Then
        Combo_Align.ListIndex = 0
    Else
        MsgBox "There is no Alignment with Sample Line Group."
        End
    End If

    Combo_BeginPt.Enabled = False
    Combo_EndPt.Enabled = False
    AddButton.Enabled = False
    DeleteButton.Visible = False
   
    
    ' progress bar settings
    ProgressBar.Min = 0
    ProgressBar.Max = 100
    ProgressBar.Visible = False
    progressBarLabel.Visible = False


    ' Get Captions
    GetCaptions

    ' list view grid setup
    ' setup columns

    Call ListView.ColumnHeaders.Add(1, , sCaptionArr(nNameIndex), 100, lvwColumnLeft)
    Call ListView.ColumnHeaders.Add(2, , sCaptionArr(nBeginPtIndex), 140, lvwColumnLeft)
    Call ListView.ColumnHeaders.Add(3, , sCaptionArr(nEndPtIndex), 140, lvwColumnLeft)

End Sub


' Do the real work of gnerating the report here
Private Sub ExecuteButton_Click()
    Dim t, pbarInc, cCount As Integer
    Dim stat As Boolean
    Dim curListItem As ListItem
    Dim exeStr As String
    
    Dim oSteam As CSTEAM

    If ListView.ListItems.Count = 0 Then
        Exit Sub
    End If

    For t = 1 To ListView.ListItems.Count
        If ListView.ListItems(t).Checked = True Then
            cCount = cCount + 1
            pbarInc = 80 / cCount
        End If
    Next

    ProgressBar.Value = 0

    progressBarLabel.Enabled = False
    progressBarLabel.Enabled = True

    progressBarLabel.Visible = True
    ProgressBar.Visible = True

    Call WriteReportHeader(g_reportFileName)

    'update progress bar
    ProgressBar.Value = 10

    
    Set oSteam = g_Steams.item(Combo_LineGroup.Text)
    
    Call AppendReport(oSteam, g_reportFileName)
    
    'update progress bar
    ProgressBar.Value = 100

    ProgressBar.Visible = False
    progressBarLabel.Visible = False


    Call WriteReportFooter(g_reportFileName)

    exeStr = "notepad.exe " & g_reportFileName
    Call Shell(exeStr, 1)

End Sub

Private Sub CancelButton_Click()

    Unload Me

End Sub

Private Sub UserForm_Terminate()

    ' clean up created objects
    Set g_oCivilApp = Nothing
    Set g_oAeccDoc = Nothing
    Set g_oAeccDb = Nothing
    Set g_Steams = Nothing
    Set g_Alignments = Nothing
    Set g_oDataToReport = Nothing
End Sub

Private Sub FileSelectionButton_Click()

    Dim fileDialog As New CFileDialog
    
    With fileDialog

        .DefaultExt = "geo"

        .DialogTitle = "Select a File"

        .Filter = "GEO Files|*.GEO"

        .FilterIndex = 1

        .MaxFileSize = 255

        .FileName = g_reportFileName

        If .Show(True) Then

            g_reportFileName = fileDialog.FileName
            ReportFileNameEdit.Text = g_reportFileName

        Else

            Exit Sub

        End If

    End With

End Sub

Private Sub GetCaptions()
    ReDim sCaptionArr(nLastIndex)
    sCaptionArr(nNameIndex) = "Name"
    sCaptionArr(nBeginPtIndex) = "Begin Point"
    sCaptionArr(nEndPtIndex) = "End Point"
End Sub

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'



Option Explicit

Public g_oDataToReport As New DataSteamNetwork

'This commented block was for html before. May be useful if reports need to be port to .net

'Function WriteReportHeader(rptName As String) As Boolean
'    Dim str As String
'    Dim unitsStr As String
'    Dim fs
'    Dim ts As TextStream
'
'    'unitsStr = GetUnitStr
'
'    Set fs = CreateObject("Scripting.FileSystemObject")
'    Set ts = fs.CreateTextFile(rptName, True)
'
'
'    str = "<HTML title='HEC-RAS Report'><Body>"
'    ts.WriteLine (str)
'    ts.WriteLine ("<Body>")
'    ts.WriteLine ("<center>")
'
'    str = "<H1>HEC-RAS Report</H1>"
'    ts.WriteLine (str)
'    ts.WriteLine ("</center>")
'
'
'
'    ' write owner and client setting
'    WriteUserSetting ts
'
'    ' data info
'    str = "Date: " & DateTime.Month(DateTime.Date) & "-" & DateTime.Day(DateTime.Date) & "-" & DateTime.Year(DateTime.Date) & "<br/>"
'    ts.WriteLine (str)
'
'    ts.WriteLine ("<HR/>")
'    ts.Close
'
'
'    Set fs = Nothing
'    Set ts = Nothing
'
'
'    WriteReportHeader = True
'End Function
'
'' Write the end of html file
'Function WriteReportFooter(rptName As String) As Boolean
'    Dim str As String
'    Dim fs, ts
'
'
'    Set fs = CreateObject("Scripting.FileSystemObject")
'
'    Set ts = fs.OpenTextFile(rptName, ForAppending)
'
'    str = "</Body></HTML>"
'
'    ts.WriteLine (str)
'    ts.Close
'
'    Set ts = Nothing
'    Set fs = Nothing
'
'
'    WriteReportFooter = True
'End Function
''
'
'
'' Append one item's report to html file
'Function AppendReport(oSteam As CSTEAM, rptName As String) As Boolean
'    On Error Resume Next
'    Dim str As String
'    Dim fs As FileSystemObject
'    Dim ts As TextStream
'    Dim sTable As String
'
'    Dim i As Long
'
''
''
'    Call ExtractData(oSteam)
'
'    Set fs = CreateObject("Scripting.FileSystemObject")
'    Set ts = fs.OpenTextFile(rptName, ForAppending)
'
'
'    'Write HEADER
'    ts.WriteLine ("<b>BEGIN HEADER:</b>")
'    WriteBlankLine 1, ts
'    sTable = "<br><table border='1' width='60%' frame='void' rules='none' id='table1' cellspacing='2'>"
'    ts.WriteLine sTable
'
'    Dim oHeader As DataHeader
'    Set oHeader = g_oDataToReport.header
'    WriteHeaderRecord "UNITS:", oHeader.Units, ts
'    WriteHeaderRecord "DTM TYPE:", oHeader.DTMType, ts
'    WriteHeaderRecord "DTM:", oHeader.DTM, ts
'    WriteHeaderRecord "NUMBER OF REACHES:", oHeader.NumberOfReaches, ts
'    WriteHeaderRecord "NUMBER OF CROSS-SECTIONS:", oHeader.NumberOfCrossSection, ts
'    WriteHeaderRecord "MAP PROJECTION:", oHeader.MapProjection, ts
'    WriteHeaderRecord "DATUM:", oHeader.Datum, ts
'    ts.WriteLine ("</Table>")
'    WriteBlankLine 1, ts
'    ts.WriteLine ("<b>END HEADER:</b><br>")
'    WriteBlankLine 2, ts
'
'    ' Write Stream NetWork
'    ts.WriteLine ("<b>BEGIN STREAM NETWORK:</b>")
'    WriteBlankLine 1, ts
'    ts.WriteLine sTable
'    Dim oEndPts As Collection
'    Set oEndPts = g_oDataToReport.EndPoints
'    For i = 1 To oEndPts.Count Step 1
'        Dim arrEndPt As Variant
'        arrEndPt = oEndPts(i)
'        WriteStreamRecord "ENDPOINT:", "", arrEndPt(nEasting) + ",", arrEndPt(nNorthing) + ",", arrEndPt(nElevation) + ",", arrEndPt(nID), ts
'    Next
'    Dim oReaches As Collection
'    Set oReaches = g_oDataToReport.Reaches
'    For i = 1 To oReaches.Count Step 1
'        Dim oReach As DataReach
'        Set oReach = oReaches.item(i)
'        WriteStreamRecord "", "", "", "", "", "", ts
'        WriteStreamRecord "REACH:", "", "", "", "", "", ts
'        WriteStreamRecord "", "STEAM ID:", oReach.SteamID, "", "", "", ts
'        WriteStreamRecord "", "REACH ID:", oReach.ReachID, "", "", "", ts
'        WriteStreamRecord "", "FROM POINT:", CStr(oReach.FromPoint), "", "", "", ts
'        WriteStreamRecord "", "TO POINT:", CStr(oReach.ToPoint), "", "", "", ts
'        WriteStreamRecord "", "CENTERLINE:", "", "", "", "", ts
'        Dim j As Long
'        For j = 1 To oReach.EndPoints.Count Step 1
'            arrEndPt = oReach.EndPoints(j)
'            WriteStreamRecord "", "", arrEndPt(nEasting) + ",", arrEndPt(nNorthing) + ",", arrEndPt(nElevation) + ",", arrEndPt(nStation), ts
'        Next
'        WriteStreamRecord "", "END:", "", "", "", "", ts
'    Next
'    ts.WriteLine ("</Table>")
'    WriteBlankLine 1, ts
'    ts.WriteLine ("<b>END STREAM NETWORK:</b><br>")
'    WriteBlankLine 2, ts
'
'    'Write Cross Section
'    ts.WriteLine ("<b>BEGIN CROSS SECTIONS:</b>")
'    ts.WriteLine sTable
'    Dim oSections As Collection
'    Dim oSection As DataSection
'    Set oSections = g_oDataToReport.CrossSections
'    For i = 1 To oSections.Count Step 1
'        Set oSection = oSections.item(i)
'        WriteStreamRecord "", "", "", "", "", "", ts
'        WriteStreamRecord "CROSS SECTION:", "", "", "", "", "", ts
'        WriteStreamRecord "", "STREAM ID:", oSection.SteamID, "", "", "", ts
'        WriteStreamRecord "", "REACH ID:", oSection.ReachID, "", "", "", ts
'        WriteStreamRecord "", "STATION:", oSection.Station, "", "", "", ts
'        WriteStreamRecord "", "CUT LINE:", "", "", "", "", ts
'        For j = 1 To oSection.CutLines.Count Step 1
'            Dim arrCutLine As Variant
'            arrCutLine = oSection.CutLines(j)
'            WriteStreamRecord "", "", arrCutLine(nEasting) + ",", arrCutLine(nNorthing), "", "", ts
'        Next j
'    Next i
'    ts.WriteLine ("</Table>")
'    WriteBlankLine 1, ts
'    ts.WriteLine ("<b>END CROSS SECTIONS:</b><br>")
'    WriteBlankLine 1, ts
'    str = DateTime.Month(DateTime.Date) & "-" & DateTime.Day(DateTime.Date) & "-" & DateTime.Year(DateTime.Date)
'    str = str & "," & DateTime.Time$
'
'    ts.WriteLine ("<b>" + "FILE COMPLETE: " + str + "</b><br>")
'    ts.Close
'
'    Set ts = Nothing
'    Set fs = Nothing
'
'
'    AppendReport = True
'
'
'End Function
''
'
'Private Function TableDataStr(ByVal sVal As String, Optional ByVal bBold As Boolean = False) As String
'    If sVal = "" Then
'        sVal = "&nbsp"
'    End If
'    If bBold = True Then
'        TableDataStr = "<td><b>" & sVal & "</b></td>"
'    Else
'        TableDataStr = "<td>" & sVal & "</td>"
'    End If
'End Function
'
'Private Function TableRecordStr(ByVal sVal As String) As String
'    TableRecordStr = "<tr>" & sVal & "</tr>"
'End Function
'
'Private Sub WriteHeaderRecord(ByVal sType As String, ByVal sValue As String, ts As TextStream)
'    Dim str As String
'    str = "<td width=20>&nbsp</td>" + TableDataStr(sType, True) + TableDataStr(sValue)
'    ts.WriteLine (TableRecordStr(str))
'End Sub
'
'Private Sub WriteStreamRecord(ByVal str1 As String, ByVal str2 As String, ByVal str3 As String, ByVal str4 As String, ByVal str5 As String, ByVal str6 As String, ts As TextStream)
'    Dim str As String
'    str = "<td width=20>&nbsp</td>" + TableDataStr(str1, True) + TableDataStr(str2, True) + TableDataStr(str3) + TableDataStr(str4) + TableDataStr(str5) + TableDataStr(str6)
'    ts.WriteLine (TableRecordStr(str))
'End Sub
'
'Private Sub WriteBlankLine(ByVal num As Long, ts As TextStream)
'    Dim i As Long
'    For i = 1 To num Step 1
'        ts.WriteLine "<br/>"
'    Next i
'
'End Sub



Function WriteReportHeader(rptName As String) As Boolean
    Dim str As String
    Dim unitsStr As String
    Dim fs
    Dim ts As TextStream

    'unitsStr = GetUnitStr

    Set fs = CreateObject("Scripting.FileSystemObject")
    Set ts = fs.CreateTextFile(rptName, True)


    str = "HEC-RAS Report"
    ts.WriteLine (str)
  
    ' data info
    str = "Date: " & DateTime.Month(DateTime.Date) & "-" & DateTime.Day(DateTime.Date) & "-" & DateTime.Year(DateTime.Date)
    ts.WriteLine (str)
    
    ts.Close


    Set fs = Nothing
    Set ts = Nothing


    WriteReportHeader = True
End Function

' Write the end of html file
Function WriteReportFooter(rptName As String) As Boolean
    Dim str As String
    Dim fs
    Dim ts As TextStream


    Set fs = CreateObject("Scripting.FileSystemObject")

    Set ts = fs.OpenTextFile(rptName, ForAppending)

    str = DateTime.Month(DateTime.Date) & "-" & DateTime.Day(DateTime.Date) & "-" & DateTime.Year(DateTime.Date)
    str = str & "," & DateTime.Time$
    
    ts.WriteLine ("FILE COMPLETE: " + str)
    
    ts.Close

    Set ts = Nothing
    Set fs = Nothing


    WriteReportFooter = True
End Function
'


' Append one item's report to html file
Function AppendReport(oSteam As CSTEAM, rptName As String) As Boolean
    On Error Resume Next
    Dim str As String
    Dim fs As FileSystemObject
    Dim ts As TextStream
    Dim sTable As String

    Dim i As Long

'
'
    Call ExtractData(oSteam)
    
    Set fs = CreateObject("Scripting.FileSystemObject")
    Set ts = fs.OpenTextFile(rptName, ForAppending)
    
    
    'Write HEADER
    WriteBlankLine 2, ts
    ts.WriteLine ("BEGIN HEADER:")
    WriteBlankLine 1, ts
    Dim indent1 As Integer, indent2 As Integer, indent3 As Integer
    indent1 = 7
    indent2 = indent1 + 6
    indent3 = indent2 + 6
    Dim oHeader As DataHeader
    Set oHeader = g_oDataToReport.header
    WriteLineWithSpaces indent1, "UNITS: " + oHeader.Units, ts
    WriteLineWithSpaces indent1, "DTM TYPE: " + oHeader.DTMType, ts
    WriteLineWithSpaces indent1, "DTM: " + oHeader.DTM, ts
    WriteLineWithSpaces indent1, "NUMBER OF REACHES: " + CStr(oHeader.NumberOfReaches), ts
    WriteLineWithSpaces indent1, "NUMBER OF CROSS-SECTIONS: " + CStr(oHeader.NumberOfCrossSection), ts
    WriteLineWithSpaces indent1, "MAP PROJECTION: " + oHeader.MapProjection, ts
    WriteLineWithSpaces indent1, "DATUM: " + oHeader.Datum, ts
   
    WriteBlankLine 1, ts
    ts.WriteLine ("END HEADER:")
    WriteBlankLine 2, ts
    
    ' Write Stream NetWork
    ts.WriteLine ("BEGIN STREAM NETWORK:")
    WriteBlankLine 1, ts
    
    Dim oEndPts As Collection
    Set oEndPts = g_oDataToReport.EndPoints
    For i = 1 To oEndPts.Count Step 1
        Dim arrEndPt As Variant
        arrEndPt = oEndPts(i)
        WriteLineWithSpaces indent1, "ENDPOINT: " + arrEndPt(nEasting) + "," + arrEndPt(nNorthing) + "," + arrEndPt(nElevation) + "," + arrEndPt(nID), ts
    Next
    
    Dim oReaches As Collection
    Set oReaches = g_oDataToReport.Reaches
    For i = 1 To oReaches.Count Step 1
        Dim oReach As DataReach
        Set oReach = oReaches.item(i)
        WriteBlankLine 1, ts
        WriteLineWithSpaces indent1, "REACH:", ts
        WriteLineWithSpaces indent2, "STEAM ID: " + oReach.SteamID, ts
        WriteLineWithSpaces indent2, "REACH ID: " + oReach.ReachID, ts
        WriteLineWithSpaces indent2, "FROM POINT: " + CStr(oReach.FromPoint), ts
        WriteLineWithSpaces indent2, "TO POINT: " + CStr(oReach.ToPoint), ts
        WriteLineWithSpaces indent2, "CENTERLINE:", ts
        Dim j As Long
        For j = 1 To oReach.EndPoints.Count Step 1
            arrEndPt = oReach.EndPoints(j)
            WriteLineWithSpaces indent3, arrEndPt(nEasting) + "," + arrEndPt(nNorthing) + "," + arrEndPt(nElevation) + "," + arrEndPt(nStation), ts
        Next
        WriteLineWithSpaces indent2, "End:", ts
    Next
   
    WriteBlankLine 1, ts
    ts.WriteLine ("END STREAM NETWORK:")
    WriteBlankLine 2, ts
    
    'Write Cross Section
    ts.WriteLine ("BEGIN CROSS SECTIONS:")
    Dim oSections As Collection
    Dim oSection As DataSection
    Set oSections = g_oDataToReport.CrossSections
    For i = 1 To oSections.Count Step 1
        Set oSection = oSections.item(i)
        WriteBlankLine 1, ts
        WriteLineWithSpaces indent1, "CROSS SECTION:", ts
        WriteLineWithSpaces indent2, "STREAM ID: " + oSection.SteamID, ts
        WriteLineWithSpaces indent2, "REACH ID: " + oSection.ReachID, ts
        WriteLineWithSpaces indent2, "STATION: " + oSection.Station, ts
        WriteLineWithSpaces indent2, "CUT LINE:", ts
        For j = 1 To oSection.CutLines.Count Step 1
            Dim arrCutLine As Variant
            arrCutLine = oSection.CutLines(j)
            WriteLineWithSpaces indent3, arrCutLine(nEasting) + "," + arrCutLine(nNorthing), ts
        Next j
    Next i
    
    WriteBlankLine 1, ts
    ts.WriteLine ("END CROSS SECTIONS:")
    WriteBlankLine 1, ts

    ts.Close

    Set ts = Nothing
    Set fs = Nothing
 
    
    AppendReport = True
    

End Function
'





Private Sub WriteBlankLine(ByVal num As Long, ts As TextStream)
    Dim i As Long
    For i = 1 To num Step 1
        ts.WriteLine ""
    Next i
    
End Sub
Private Sub WriteLineWithSpaces(ByVal numberOfSpaces As Integer, ByVal str As String, ts As TextStream)
    Dim i As Integer
    For i = 0 To numberOfSpaces Step 1
        str = " " + str
    Next i
    ts.WriteLine str
End Sub

Private Function GetSpaces(num As Integer) As String
    Dim i As Integer
    For i = 1 To num Step 1
        GetSpaces = GetSpaces + " "
    Next i
End Function

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub HECRAS_RunReport()
    On Error Resume Next
    
    Dim rptDlg As ReportForm_HECRAS
    
    ' initialize C3D
    If InitCivil3D = False Then
        Call MsgBox("Error: Unable to initialize Civil 3D Object Model", vbOKOnly, "Civil 3D Reports")
        Exit Sub
    End If
    
    On Error Resume Next
    Err.Clear
    ' Create report dialog and display it
    Set rptDlg = New ReportForm_HECRAS
    If Err.Number <> 0 Then
        Exit Sub
    End If
    rptDlg.Show
    
    Set rptDlg = Nothing
End Sub
