Attribute VB_Name = "Format"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

'-----------------------------------------------------------------------
'   set rawAngle(radian) into [0,2pi].
'-----------------------------------------------------------------------
Function AdjustAngle2PI(ByVal rawAngle As Double) As Double
    pi = 4 * Atn(1)
    Do While rawAngle >= pi * 2
        rawAngle = rawAngle - pi * 2
    Loop
    Do While rawAngle < 0#
        rawAngle = rawAngle + pi * 2
    Loop
    AdjustAngle2PI = rawAngle
End Function

'-----------------------------------------------------------------------
'   rounds off values and returns a string.
'-----------------------------------------------------------------------
Function RoundVal(value As Double, prec As Integer, Optional roundType As AeccRoundingType = aeccRoundingNormal) As String
    If Abs(value) < 10000000000# Then
        Dim dNewValue As Double
        dNewValue = value
        Dim sNewValue As String
        Select Case prec
            Case 0
                sNewValue = VBA.Format(dNewValue, "#0")
            Case 1
                sNewValue = VBA.Format(dNewValue, "#0.0")
            Case 2
                sNewValue = VBA.Format(dNewValue, "#0.00")
            Case 3
                sNewValue = VBA.Format(dNewValue, "#0.000")
            Case 4
                sNewValue = VBA.Format(dNewValue, "#0.0000")
            Case 5
                sNewValue = VBA.Format(dNewValue, "#0.00000")
            Case 6
                sNewValue = VBA.Format(dNewValue, "#0.000000")
            Case 7
                sNewValue = VBA.Format(dNewValue, "#0.0000000")
            Case 8
                sNewValue = VBA.Format(dNewValue, "#0.00000000")
        End Select
        
        If roundType <> aeccRoundingNormal Then
            dNewValue = CDbl(sNewValue)
            Dim dLastBit As Double
            dLastBit = 10 ^ (-1# * prec)
            If roundType = aeccRoundingTruncate Then
                If Abs(dNewValue) > Abs(value) Then
                    dNewValue = Abs(dNewValue) - dLastBit
                    If value < 0 Then
                        dNewValue = -1# * dNewValue
                    End If
                End If
            ElseIf roundType = aeccRoundingUp Then
                If Abs(dNewValue) < Abs(value) Then
                    dNewValue = Abs(dNewValue) + dLastBit
                    If value < 0 Then
                        dNewValue = -1# * dNewValue
                    End If
                End If
            End If
            sNewValue = CStr(dNewValue)
        End If
        RoundVal = sNewValue
    Else
        RoundVal = VBA.Format(value, "0.00000000000000E+00")
    End If
End Function
'-----------------------------------------------------------------------
'   format a grade
'   e.g.:  1:3.232
'   Note: given the originate gradeFormatType aeccGradeSlopeFormatDecimal
'         this function don't take care aeccGradeSlopeFormatRiseRun & aeccGradeSlopeFormatRunRise,which will be in FormatSlope
'-----------------------------------------------------------------------
Function FormatGrade(dGrade As Double, Optional grdFormat As AeccGradeSlopeFormatType = aeccGradeSlopeFormatPercent, _
                                       Optional grdPrec As Integer = 3, _
                                       Optional grdRounding As AeccRoundingType = aeccRoundingNormal, _
                                       Optional grdSign As AeccSignType = aeccSignNegative) As String
    Dim sPreSign As String, sPostSign As String
    Select Case grdSign
        Case aeccSignAlways
            If dGrade < 0# Then
                sPreSign = "-"
            Else
                sPreSign = "+"
            End If
        Case aeccSignBracketNegative
            If dGrade < 0# Then
                sPreSign = "("
                sPostSign = ")"
            End If
        Case aeccSignNegative
            If dGrade < 0# Then
                sPreSign = "-"
            End If
    End Select
    dGrade = Abs(dGrade)
    
    Dim sGrade As String
    Select Case grdFormat
        Case aeccGradeSlopeFormatDecimal
            dGrade = RoundVal(dGrade, grdPrec, grdRounding)
            sGrade = CStr(dGrade)
        Case aeccGradeSlopeFormatPercent
            dGrade = dGrade * 100#
            dGrade = RoundVal(dGrade, grdPrec, grdRounding)
            sGrade = CStr(dGrade) + "%"
    End Select
    
    FormatGrade = sPreSign + sGrade + sPostSign
End Function

'-----------------------------------------------------------------------
'   format a volume
'   e.g.:  +35.34Cu.Yd. +35.34Cu.M. +35.34Cu.Ft.
'   Note: the originate unitType depends on drawing's AeccSettingsUnitZone
'-----------------------------------------------------------------------
Function FormatArea(dArea As Double, Optional areaUnit As AeccAreaUnitType = aeccAreaUnitSquareFoot, _
                                        Optional volPrec As Integer = 4, _
                                        Optional volRounding As AeccRoundingType = aeccRoundingNormal, _
                                        Optional volSign As AeccSignType = aeccSignNegative) As String
    
    Dim sPreSign As String, sPostSign As String
    Select Case grdSign
        Case aeccSignAlways
            If dArea < 0# Then
                sPreSign = "-"
            Else
                sPreSign = "+"
            End If
        Case aeccSignBracketNegative
            If dArea < 0# Then
                sPreSign = "("
                sPostSign = ")"
            End If
        Case aeccSignNegative
            If dArea < 0# Then
                sPreSign = "-"
            End If
    End Select
    dArea = Abs(dArea)
    'trans dDis to aeccCoordinateUnitMeter
    Dim disOriUnit As AeccDrawingUnitType
    disOriUnit = getAeccDb.settings.DrawingSettings.UnitZoneSettings.DrawingUnits
    If disOriUnit = aeccDrawingUnitFeet Then
        dArea = dArea * (0.3048006096012 ^ 2)
    End If
    
    Dim sArea As String
    Select Case areaUnit
        Case aeccAreaUnitSquareMeter  'aeccVolumeUnitCubicMeter
            dArea = RoundVal(dArea, volPrec, volRounding)
            sArea = CStr(dArea) + "Sq.M."
        Case aeccAreaUnitSquareFoot
            dArea = dArea / (0.3048006096012 ^ 2)
            dArea = RoundVal(dArea, volPrec, volRounding)
            sArea = CStr(dArea) + "Sq.Ft."
        Case aeccAreaUnitAcre
            dArea = dArea * 0.0002471
            dArea = RoundVal(dArea, volPrec, volRounding)
            sArea = CStr(dArea) + "Acre"
        Case aeccAreaUnitHectare
            dArea = dArea * 0.0001
            dArea = RoundVal(dArea, volPrec, volRounding)
            sArea = CStr(dArea) + "Hectare"
        Case aeccAreaUnitSquareKilometer
            dArea = dArea * 0.000001
            dArea = RoundVal(dArea, volPrec, volRounding)
            sArea = CStr(dArea) + "Sq.Km."
        Case aeccAreaUnitSquareMile
            dArea = dArea * 0.000000386
            dArea = RoundVal(dArea, volPrec, volRounding)
            sArea = CStr(dArea) + "Sq.Mile"
        Case aeccAreaUnitSquareYard
            dArea = dArea * 1.196
            dArea = RoundVal(dArea, volPrec, volRounding)
            sArea = CStr(dArea) + "Sq.Yd."
    End Select
    FormatArea = sPreSign + sArea + sPostSign
End Function


'-----------------------------------------------------------------------
'   format a volume
'   e.g.:  +35.34Cu.Yd. +35.34Cu.M. +35.34Cu.Ft.
'   Note: the originate unitType depends on drawing's AeccSettingsUnitZone
'-----------------------------------------------------------------------
Function FormatVolume(dVol As Double, Optional volUnit As AeccVolumeUnitType = aeccVolumeUnitCubicFoot, _
                                        Optional volPrec As Integer = 4, _
                                        Optional volRounding As AeccRoundingType = aeccRoundingNormal, _
                                        Optional volSign As AeccSignType = aeccSignNegative) As String
    Dim sPreSign As String, sPostSign As String
    Select Case grdSign
        Case aeccSignAlways
            If dVol < 0# Then
                sPreSign = "-"
            Else
                sPreSign = "+"
            End If
        Case aeccSignBracketNegative
            If dVol < 0# Then
                sPreSign = "("
                sPostSign = ")"
            End If
        Case aeccSignNegative
            If dVol < 0# Then
                sPreSign = "-"
            End If
    End Select
    dVol = Abs(dVol)
    
    'trans dDis to aeccCoordinateUnitMeter
    Dim disOriUnit As AeccDrawingUnitType
    disOriUnit = getAeccDb.settings.DrawingSettings.UnitZoneSettings.DrawingUnits
    If disOriUnit = aeccDrawingUnitFeet Then
        dVol = dVol * (0.3048006096012 ^ 3)
    End If
    
    Dim sVol As String
    Select Case volUnit
        Case aeccVolumeUnitCubicMeter
            dVol = RoundVal(dVol, volPrec, volRounding)
            sVol = CStr(dVol) + "Cu.M."
        Case aeccVolumeUnitCubicFoot
            dVol = dVol / (0.3048006096012 ^ 3)
            dVol = RoundVal(dVol, volPrec, volRounding)
            sVol = CStr(dVol) + "Cu.Ft"
        Case aeccVolumeUnitCubicInch
            dVol = dVol * ((12# / 0.3048006096012) ^ 3)
            dVol = RoundVal(dVol, volPrec, volRounding)
            sVol = CStr(dVol) + "Cu.Inch"
        Case aeccVolumeUnitCubicYard
            dVol = dVol / ((3# * 0.3048006096012) ^ 3)
            dVol = RoundVal(dVol, volPrec, volRounding)
            sVol = CStr(dVol) + "Cu.Yd"
    End Select
    FormatVolume = sPreSign + sVol + sPostSign
End Function

'-----------------------------------------------------------------------
'   format a distance
'   e.g.:  +35.34(f)
'   Note: the originate unitType depends on drawing's AeccSettingsUnitZone
'-----------------------------------------------------------------------
Function FormatDistance(dDis As Double, Optional disUnit As AeccCoordinateUnitType = aeccCoordinateUnitFoot, _
                                        Optional disPrec As Integer = 6, _
                                        Optional disRounding As AeccRoundingType = aeccRoundingNormal, _
                                        Optional disSign As AeccSignType = aeccSignNegative, _
                                        Optional unitIndicator As Boolean = True) As String
    Dim sPreSign As String, sPostSign As String
    Select Case disSign
        Case aeccSignAlways
            If dDis < 0# Then
                sPreSign = "-"
            Else
                sPreSign = "+"
            End If
        Case aeccSignBracketNegative
            If dDis < 0# Then
                sPreSign = "("
                sPostSign = ")"
            End If
        Case aeccSignNegative
            If dDis < 0# Then
                sPreSign = "-"
            End If
    End Select
    dDis = Abs(dDis)
    
    'trans dDis to aeccCoordinateUnitMeter
    Dim disOriUnit As AeccDrawingUnitType
    disOriUnit = getAeccDb.settings.DrawingSettings.UnitZoneSettings.DrawingUnits
    If disOriUnit = aeccDrawingUnitFeet Then
        dDis = dDis * 0.3048006096012
    End If
    
    Dim sDis As String
    Select Case disUnit
        Case aeccCoordinateUnitMeter
            dDis = RoundVal(dDis, disPrec, disRounding)
            sDis = CStr(dDis)
            If unitIndicator = True Then
                sDis = sDis + "m"
            End If
            
        Case aeccCoordinateUnitKilometer
            dDis = dDis / 1000#
            dDis = RoundVal(dDis, disPrec, disRounding)
            sDis = CStr(dDis)
            If unitIndicator = True Then
                sDis = sDis + "km"
            End If
            
        Case aeccCoordinateUnitFoot
            dDis = dDis / 0.3048006096012
            dDis = RoundVal(dDis, disPrec, disRounding)
            sDis = CStr(dDis)
            If unitIndicator = True Then
                sDis = sDis + "'"
            End If
            
        Case aeccCoordinateUnitInch
            dDis = dDis * 12# / 0.3048006096012
            dDis = RoundVal(dDis, disPrec, disRounding)
            sDis = CStr(dDis)
            If unitIndicator = True Then
                sDis = sDis + """"
            End If
            
        Case aeccCoordinateUnitYard
            dDis = dDis / 3# / 0.3048006096012
            dDis = RoundVal(dDis, disPrec, disRounding)
            sDis = CStr(dDis)
            If unitIndicator = True Then
                sDis = sDis + "yd"
            End If
            
        Case aeccCoordinateUnitMile
            dDis = dDis / 1760# / 3# / 0.3048006096012
            dDis = RoundVal(dDis, disPrec, disRounding)
            sDis = CStr(dDis)
            If unitIndicator = True Then
                sDis = sDis + "miles"
            End If
            
    End Select
    FormatDistance = sPreSign + sDis + sPostSign
End Function

'-----------------------------------------------------------------------
'   format a radian angle
'   e.g.:  65^34'32.32"
'   Note:  do not take care dRadAng's scope
'-----------------------------------------------------------------------
Function FormatAngle(dRadAng As Double, Optional angUnit As AeccAngleUnitType = aeccAngleUnitDegree, Optional angPrec As Integer = 6, _
                                        Optional angRounding As AeccRoundingType = aeccRoundingNormal, Optional angFormat As AeccFormatType = aeccFormatDegreeMinuteSecond, _
                                        Optional angSign As AeccSignType = aeccSignNegative) As String
    Dim sPreSign As String, sPostSign As String
    Dim pi As Double
    pi = 4 * Atn(1)
    Select Case angSign
        Case aeccSignAlways
            If dRadAng < 0# Then
                sPreSign = "-"
            Else
                sPreSign = "+"
            End If
        Case aeccSignBracketNegative
            If dRadAng < 0# Then
                sPreSign = "("
                sPostSign = ")"
            End If
        Case aeccSignNegative
            If dRadAng < 0# Then
                sPreSign = "-"
            End If
    End Select
    dRadAng = Abs(dRadAng)
    
    Dim sAngle As String
    Select Case angUnit
        Case aeccAngleUnitDegree
            Dim dAng As Double
            dAng = dRadAng * 180# / pi
            Dim iDeg As Integer, iMin As Integer, iSec As Integer
            Dim iCentSec As Integer

            If angFormat <> aeccFormatDecimal Then
                iDeg = Int(dAng)
                dAng = (dAng - iDeg) * 60
                iMin = Int(dAng)
                dAng = (dAng - iMin) * 60
                iSec = Int(dAng)
                dAng = dAng - iSec
                Dim iPrec As Integer
                iPrec = angPrec - 4
                Do While iPrec > 0
                        dAng = dAng * 10
                        iPrec = iPrec - 1
                Loop
                iCentSec = Int(dAng)
                
                Dim sDeg As String, sMin As String, sSec As String, sCentSec As String
                sDeg = CStr(iDeg)
                sMin = CStr(iMin)
                If Len(sMin) = 1 Then
                    sMin = "0" & sMin
                End If
                sSec = CStr(iSec)
                If Len(sSec) = 1 Then
                    sSec = "0" & sSec
                End If
                sCentSec = CStr(iCentSec)
            Else
                dAng = RoundVal(dAng, angPrec, angRounding)
            End If
                            
            Select Case angFormat
                Case aeccFormatDecimal
                    sAngle = CStr(dAng) + " (d)"
                Case aeccFormatDecimalDegreeMinuteSecond
                    sAngle = sDeg & "." & sMin & sSec & sCnetSec & " (dms)"
                Case aeccFormatDegreeMinuteSecond
                    sAngle = sDeg & Chr(176) & sMin & "'" & sSec & "." & sCentSec & """"
                Case aeccFormatDegreeMinuteSecondSpaced
                    sAngle = sDeg & Chr(176) & " " & sMin & "' " & sSec & "." & sCentSec & """"
            End Select
        Case aeccAngleUnitGrad
            dRadAng = dRadAng * 200# / pi
            dRadAng = RoundVal(dRadAng, angPrec, angRounding)
            sAngle = CStr(dRadAng) + " (g)"
        Case aeccAngleUnitRadian
            dRadAng = dRadAng
            dRadAng = RoundVal(dRadAng, angPrec, angRounding)
            sAngle = CStr(dRadAng) + " (r)"
    End Select 'angUnit
    FormatAngle = sPreSign + sAngle + sPostSign
End Function

'-----------------------------------------------------------------------
'   format a radian angle to direction.
'   e.g.:  N65^34'32.32"E
'   Note:  dRadAng is start from x-axis and rotate counterclockwise
'-----------------------------------------------------------------------
Function FormatDirection(dRadAng As Double, Optional angUnit As AeccAngleUnitType = aeccAngleUnitDegree, Optional angPrec As Integer = 6, _
                                            Optional angRounding As AeccRoundingType = aeccRoundingNormal, Optional angFormat As AeccFormatType = aeccFormatDegreeMinuteSecond, _
                                            Optional angDirection As AeccDirectionType = aeccDirectionShortName, Optional angCap As AeccCapitalizationType = aeccCapitalizationUpperCase, _
                                            Optional angSign As AeccSignType = aeccSignNegative, Optional angMeasType As AeccMeasurementType = aeccMeasurementBearings, _
                                            Optional angBearQuand As AeccBearingQuadrantType = aeccBearingQuadrantNorthEast) As String
    'step 1: get proper dRadAng considering angMeasType and preFixString/postFixString
    Dim pi As Double
    pi = 4 * Atn(1)
    dRadAng = AdjustAngle2PI(dRadAng)
    dRadAng = dRadAng * 180# / pi
    
    Dim sPrefix As String, sPostfix As String
    Select Case angMeasType
        Case aeccMeasurementBearings
            If dRadAng >= 90 And dRadAng < 180 Then
                dRadAng = dRadAng - 90#
                Select Case angDirection
                    Case aeccDirectionLongName
                        Select Case angCap
                            Case aeccCapitalizationLowerCase
                                sPrefix = "north": sPostfix = "west"
                            Case aeccCapitalizationPreserveCase
                                sPrefix = "NORTH": sPostfix = "WEST"
                            Case aeccCapitalizationTitleCaps
                                sPrefix = "North": sPostfix = "West"
                            Case aeccCapitalizationUpperCase
                                sPrefix = "NORTH": sPostfix = "WEST"
                        End Select
                    Case aeccDirectionShortName
                        Select Case angCap
                            Case aeccCapitalizationLowerCase
                                sPrefix = "n": sPostfix = "w"
                            Case aeccCapitalizationPreserveCase
                                sPrefix = "N": sPostfix = "W"
                            Case aeccCapitalizationTitleCaps
                                sPrefix = "N": sPostfix = "W"
                            Case aeccCapitalizationUpperCase
                                sPrefix = "N": sPostfix = "W"
                        End Select
                    Case aeccDirectionLongNameSpaced
                        Select Case angCap
                            Case aeccCapitalizationLowerCase
                                sPrefix = "north ": sPostfix = " west"
                            Case aeccCapitalizationPreserveCase
                                sPrefix = "NORTH ": sPostfix = " WEST"
                            Case aeccCapitalizationTitleCaps
                                sPrefix = "North ": sPostfix = " West"
                            Case aeccCapitalizationUpperCase
                                sPrefix = "NORTH ": sPostfix = " WEST"
                        End Select
                    Case aeccDirectionShortNameSpaced
                        Select Case angCap
                            Case aeccCapitalizationLowerCase
                                sPrefix = "n ": sPostfix = " w"
                            Case aeccCapitalizationPreserveCase
                                sPrefix = "N ": sPostfix = " W"
                            Case aeccCapitalizationTitleCaps
                                sPrefix = "N ": sPostfix = " W"
                            Case aeccCapitalizationUpperCase
                                sPrefix = "N ": sPostfix = " W"
                        End Select
                End Select 'angDirection
                
            ElseIf dRadAng >= 180 And dRadAng < 270 Then
                dRadAng = 270# - dRadAng
                Select Case angDirection
                    Case aeccDirectionLongName
                        Select Case angCap
                            Case aeccCapitalizationLowerCase
                                sPrefix = "south": sPostfix = "west"
                            Case aeccCapitalizationPreserveCase
                                sPrefix = "SOUTH": sPostfix = "WEST"
                            Case aeccCapitalizationTitleCaps
                                sPrefix = "South": sPostfix = "West"
                            Case aeccCapitalizationUpperCase
                                sPrefix = "SOUTH": sPostfix = "WEST"
                        End Select
                    Case aeccDirectionShortName
                        Select Case angCap
                            Case aeccCapitalizationLowerCase
                                sPrefix = "s": sPostfix = "w"
                            Case aeccCapitalizationPreserveCase
                                sPrefix = "S": sPostfix = "W"
                            Case aeccCapitalizationTitleCaps
                                sPrefix = "S": sPostfix = "W"
                            Case aeccCapitalizationUpperCase
                                sPrefix = "S": sPostfix = "W"
                        End Select
                    Case aeccDirectionLongNameSpaced
                        Select Case angCap
                            Case aeccCapitalizationLowerCase
                                sPrefix = "south ": sPostfix = " west"
                            Case aeccCapitalizationPreserveCase
                                sPrefix = "SOUTH ": sPostfix = " WEST"
                            Case aeccCapitalizationTitleCaps
                                sPrefix = "South ": sPostfix = " West"
                            Case aeccCapitalizationUpperCase
                                sPrefix = "SOUTH ": sPostfix = " WEST"
                        End Select
                    Case aeccDirectionShortNameSpaced
                        Select Case angCap
                            Case aeccCapitalizationLowerCase
                                sPrefix = "s ": sPostfix = " w"
                            Case aeccCapitalizationPreserveCase
                                sPrefix = "S ": sPostfix = " W"
                            Case aeccCapitalizationTitleCaps
                                sPrefix = "S ": sPostfix = " W"
                            Case aeccCapitalizationUpperCase
                                sPrefix = "S ": sPostfix = " W"
                        End Select
                End Select 'angDirection
                
            ElseIf dRadAng >= 270 And dRadAng <= 360 Then
                dRadAng = dRadAng - 270#
                Select Case angDirection
                    Case aeccDirectionLongName
                        Select Case angCap
                            Case aeccCapitalizationLowerCase
                                sPrefix = "south": sPostfix = "east"
                            Case aeccCapitalizationPreserveCase
                                sPrefix = "SOUTH": sPostfix = "EAST"
                            Case aeccCapitalizationTitleCaps
                                sPrefix = "South": sPostfix = "East"
                            Case aeccCapitalizationUpperCase
                                sPrefix = "SOUTH": sPostfix = "EAST"
                        End Select
                    Case aeccDirectionShortName
                        Select Case angCap
                            Case aeccCapitalizationLowerCase
                                sPrefix = "s": sPostfix = "e"
                            Case aeccCapitalizationPreserveCase
                                sPrefix = "S": sPostfix = "E"
                            Case aeccCapitalizationTitleCaps
                                sPrefix = "S": sPostfix = "E"
                            Case aeccCapitalizationUpperCase
                                sPrefix = "S": sPostfix = "E"
                        End Select
                    Case aeccDirectionLongNameSpaced
                        Select Case angCap
                            Case aeccCapitalizationLowerCase
                                sPrefix = "south ": sPostfix = " east"
                            Case aeccCapitalizationPreserveCase
                                sPrefix = "SOUTH ": sPostfix = " EAST"
                            Case aeccCapitalizationTitleCaps
                                sPrefix = "South ": sPostfix = " East"
                            Case aeccCapitalizationUpperCase
                                sPrefix = "SOUTH ": sPostfix = " EAST"
                        End Select
                    Case aeccDirectionShortNameSpaced
                        Select Case angCap
                            Case aeccCapitalizationLowerCase
                                sPrefix = "s ": sPostfix = " e"
                            Case aeccCapitalizationPreserveCase
                                sPrefix = "S ": sPostfix = " E"
                            Case aeccCapitalizationTitleCaps
                                sPrefix = "S ": sPostfix = " E"
                            Case aeccCapitalizationUpperCase
                                sPrefix = "S ": sPostfix = " E"
                        End Select
                End Select 'angDirection
                
            Else
                dRadAng = 90# - dRadAng
                Select Case angDirection
                    Case aeccDirectionLongName
                        Select Case angCap
                            Case aeccCapitalizationLowerCase
                                sPrefix = "north": sPostfix = "east"
                            Case aeccCapitalizationPreserveCase
                                sPrefix = "NORTH": sPostfix = "EAST"
                            Case aeccCapitalizationTitleCaps
                                sPrefix = "North": sPostfix = "East"
                            Case aeccCapitalizationUpperCase
                                sPrefix = "NORTH": sPostfix = "EAST"
                        End Select
                    Case aeccDirectionShortName
                        Select Case angCap
                            Case aeccCapitalizationLowerCase
                                sPrefix = "n": sPostfix = "e"
                            Case aeccCapitalizationPreserveCase
                                sPrefix = "N": sPostfix = "E"
                            Case aeccCapitalizationTitleCaps
                                sPrefix = "N": sPostfix = "E"
                            Case aeccCapitalizationUpperCase
                                sPrefix = "N": sPostfix = "E"
                        End Select
                    Case aeccDirectionLongNameSpaced
                        Select Case angCap
                            Case aeccCapitalizationLowerCase
                                sPrefix = "north ": sPostfix = " east"
                            Case aeccCapitalizationPreserveCase
                                sPrefix = "NORTH ": sPostfix = " EAST"
                            Case aeccCapitalizationTitleCaps
                                sPrefix = "North ": sPostfix = " East"
                            Case aeccCapitalizationUpperCase
                                sPrefix = "NORTH ": sPostfix = " EAST"
                        End Select
                    Case aeccDirectionShortNameSpaced
                        Select Case angCap
                            Case aeccCapitalizationLowerCase
                                sPrefix = "n ": sPostfix = " e"
                            Case aeccCapitalizationPreserveCase
                                sPrefix = "N ": sPostfix = " E"
                            Case aeccCapitalizationTitleCaps
                                sPrefix = "N ": sPostfix = " E"
                            Case aeccCapitalizationUpperCase
                                sPrefix = "N ": sPostfix = " E"
                        End Select
                End Select 'angDirection
            End If
        'Case aeccMeasurementBearings End
        Case aeccMeasurementNorthAzimuth
            dRadAng = 450 - dRadAng
            If dRadAng >= 360 Then
                dRadAng = dRadAng - 360
            End If
            sPrefix = "N "
        Case aeccMeasurementSouthAzimuth
            dRadAng = 270 - dRadAng
            If dRadAng <= 0 Then
                dRadAng = dRadAng + 360
            End If
            sPrefix = "S "
    End Select 'angMeasType
    
    'step 2: get dRadAng's string
    Dim sAngle As String
    Select Case angUnit
        Case aeccAngleUnitDegree
            Dim dAng As Double
            dAng = dRadAng
            Dim iDeg As Integer, iMin As Integer, iSec As Integer
            Dim iCentSec As Integer

            If angFormat <> aeccFormatDecimal Then
                iDeg = Int(dAng)
                dAng = (dAng - iDeg) * 60
                iMin = Int(dAng)
                dAng = (dAng - iMin) * 60
                iSec = Int(dAng)
                dAng = dAng - iSec
                Dim iPrec As Integer
                iPrec = angPrec - 4
                Do While iPrec > 0
                        dAng = dAng * 10
                        iPrec = iPrec - 1
                Loop
                iCentSec = Int(dAng)
                
                Dim sDeg As String, sMin As String, sSec As String, sCentSec As String
                sDeg = CStr(iDeg)
                sMin = CStr(iMin)
                If Len(sMin) = 1 Then
                    sMin = "0" & sMin
                End If
                sSec = CStr(iSec)
                If Len(sSec) = 1 Then
                    sSec = "0" & sSec
                End If
                sCentSec = CStr(iCentSec)
            Else
                dAng = RoundVal(dAng, angPrec, angRounding)
            End If
                            
            Select Case angFormat
                Case aeccFormatDecimal
                    sAngle = CStr(dAng)
                    sPostfix = sPostfix + " (d)"
                Case aeccFormatDecimalDegreeMinuteSecond
                    sAngle = sDeg & "." & sMin & sSec & sCnetSec
                    sPostfix = sPostfix + " (dms)"
                Case aeccFormatDegreeMinuteSecond
                    sAngle = sDeg & Chr(176) & sMin & "'" & sSec & "." & sCentSec & """"
                Case aeccFormatDegreeMinuteSecondSpaced
                    sAngle = sDeg & Chr(176) & " " & sMin & "' " & sSec & "." & sCentSec & """"
            End Select
        Case aeccAngleUnitGrad
            dRadAng = dRadAng * 400 / 360
            dRadAng = RoundVal(dRadAng, angPrec, angRounding)
            sAngle = CStr(dRadAng)
            sPostfix = sPostfix + " (g)"
        Case aeccAngleUnitRadian
            dRadAng = dRadAng * pi / 360
            dRadAng = RoundVal(dRadAng, angPrec, angRounding)
            sAngle = CStr(dRadAng)
            sPostfix = sPostfix + " (r)"
    End Select 'angUnit
    FormatDirection = sPrefix + sAngle + sPostfix
End Function

Attribute VB_Name = "General"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

'mod version

Public Const MODVER = "7.0"

' Help file window handle
Public ReportsHH_hWnd As Long
Public Const HH_HELP_CONTEXT = &HF            ' Display mapped numeric value in dwData.

' CommonDialog control flags
Public Const IDH_AECC_REPORTS_CREATE_PI_STATION_REPORT = 5789      '  Create Reports – PI Station Report      18-Oct
Public Const IDH_AECC_REPORTS_CREATE_INCREMENTAL_STATIONING_REPORT_ALIGNMENTS = 5790      '  Create Reports – Incremental Stationing Report (Alignments)     18-Oct
Public Const IDH_AECC_REPORTS_CREATE_STAKEOUT_ALIGNMENT_REPORT = 5791     '  Create Reports – Stakeout Alignment Report      18-Oct
Public Const IDH_AECC_REPORTS_CREATE_PVI_STATION_AND_CURVE_REPORT = 5792      '  Create Reports – PVI Station and Curve Report       18-Oct
Public Const IDH_AECC_REPORTS_CREATE_INCREMENTAL_STATIONING_REPORT_PROFILES = 5793    '  Create Reports – Incremental Stationing Report (Profiles)       18-Oct
Public Const IDH_AECC_REPORTS_CREATE_VERTICAL_CURVE_REPORT = 5794     '  Create Reports – Vertical Curve Report      18-Oct
Public Const IDH_AECC_REPORTS_CREATE_SLOPE_GRADE_REPORT = 5795    '  Create Reports – Slope Grade Report         18-Oct
Public Const IDH_AECC_REPORTS_CREATE_SECTION_DESIGN_REPORT = 5796     '  Create Reports – Section Design Report      18-Oct
Public Const IDH_AECC_REPORTS_CREATE_PARCEL_VOLUMES_REPORT = 5797     '  Create Reports – Parcel Volumes Report      18-Oct
Public Const IDH_AECC_REPORTS_CREATE_PARCEL_MAPCHECK_REPORT = 5798    '  Create Reports – Parcel Mapcheck Report     18-Oct
Public Const IDH_AECC_REPORTS_CREATE_STATION_OFFSET_TO_POINTS_REPORT = 5799   '  Create Reports – Station Offset to Points       18-Oct
Public Const IDH_AECC_REPORTS_CREATE_HEC_RAS_REPORT = 5800   'Create Reports - HEC-RAS
'-----------------------------------------------------------------------
' declare the HtmlHelp function, used by the Help buttons in the dialog boxes
' and IsWindow to test to see if the help file needs to be closed on exit
'-----------------------------------------------------------------------
Public Declare Function ReportsHtmlHelp Lib "hhctrl.ocx" Alias "HtmlHelpA" _
         (ByVal hwndCaller As Long, ByVal pszFile As String, _
         ByVal uCommand As Long, ByVal dwData As Long) As Long

Private Declare Function ShellExecute _
                            Lib "shell32.dll" _
                            Alias "ShellExecuteA" ( _
                            ByVal hwnd As Long, _
                            ByVal lpOperation As String, _
                            ByVal lpFile As String, _
                            ByVal lpParameters As String, _
                            ByVal lpDirectory As String, _
                            ByVal nShowCmd As Long) _
                            As Long

Function getReportsHelpFile() As String
    getReportsHelpFile = AcadApplication.Path & "\Help\" & "Civil3D2008.chm"
End Function


Function getAeccDb() As AeccDatabase
    Dim oApp As AcadApplication
    Set oApp = ThisDrawing.Application
    Const sAppName = "AeccXUiLand.AeccApplication." + MODVER
    Dim oCivilApp As AeccApplication
    Set oCivilApp = oApp.GetInterfaceObject(sAppName)
    Dim oAeccDoc As AeccDocument
    Set oAeccDoc = oCivilApp.ActiveDocument
    Set getAeccDb = oAeccDoc.Database
End Function


Public Function GetRawStation(ByVal equaStation As String) As Double
    Dim tmpStr As String
    Dim station As Double
    tmpStr = Replace(equaStation, "+", "", 1, 1)
    GetRawStation = Val(tmpStr)
End Function


Public Function GetUnitStr() As String
    Dim settings
    Dim unitsStr As String
    
    Set settings = g_oAeccDb.settings.DrawingSettings.AmbientSettings.DistanceSettings.Unit
    If settings = AeccCoordinateUnitType.aeccCoordinateUnitFoot Then
        unitsStr = "Feet"
    ElseIf settings = AeccCoordinateUnitType.aeccCoordinateUnitMeter Then
        unitsStr = "Meters"
    End If
    GetUnitStr = unitsStr
End Function

Public Sub QuickSort(varArray As Variant, Optional iLeft As Integer = -2, Optional iRight As Integer = -2)
    Dim i As Integer
    Dim j As Integer
    Dim iMid As Integer
    
    Dim varTestValue As Variant
    
    If iLeft = -2 Then iLeft = LBound(varArray)
    If iRight = -2 Then iRight = UBound(varArray)
    
    If iLeft < iRight Then
        iMid = (iLeft + iRight) \ 2
        varTestValue = varArray(iMid)
        i = iLeft
        j = iRight
        
        Do
            Do While varArray(i) < varTestValue
                i = i + 1
            Loop
            Do While varArray(j) > varTestValue
                j = j - 1
            Loop
            If i <= j Then
                SwapElements varArray, i, j
                i = i + 1
                j = j - 1
            End If
        Loop Until i > j
        'To optimize the sort, always sort the smallest segment first
        If j <= iMid Then
            Call QuickSort(varArray, iLeft, j)
            Call QuickSort(varArray, i, iRight)
        Else
            Call QuickSort(varArray, i, iRight)
            Call QuickSort(varArray, iLeft, j)
        End If
    End If
End Sub

Public Sub SwapElements(varItems As Variant, iItem1 As Integer, iItem2 As Integer)
    Dim varTemp As Variant
    varTemp = varItems(iItem2)
    varItems(iItem2) = varItems(iItem1)
    varItems(iItem1) = varTemp
End Sub

Public Sub SwapVars(varItem1 As Variant, varItem2 As Variant)
    Dim varTemp As Variant
    varTemp = varItem2
    varItem2 = varItem1
    varItem1 = varTemp
End Sub

Public Sub OpenFileByDefaultBrowser(fileName As String)
    Call ShellExecute(0, "open", fileName, 0, 0, 1)
End Sub

Attribute VB_Name = "Regestry"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

'-----------------------------------------------------------------------
' registry functions to get the language settings
'-----------------------------------------------------------------------
Public Const HKEY_CLASSES_ROOT = &H80000000
Public Const HKEY_CURRENT_USER = &H80000001
Public Const HKEY_LOCAL_MACHINE = &H80000002
Public Const HKEY_USERS = &H80000003
Public Const HKEY_PERFORMANCE_DATA = &H80000004
Public Const HKEY_CURRENT_CONFIG = &H80000005
Public Const HKEY_DYN_DATA = &H80000006
Public Const REG_SZ = 1                         ' Unicode nul terminated string
Public Const REG_BINARY = 3                     ' Free form binary
Public Const REG_DWORD = 4                      ' 32-bit number
Public Const ERROR_SUCCESS = 0&

Public Declare Function RegOpenKey Lib "advapi32.dll" Alias "RegOpenKeyA" (ByVal hKey As Long, ByVal lpSubKey As String, phkResult As Long) As Long
Public Declare Function RegCloseKey Lib "advapi32.dll" (ByVal hKey As Long) As Long
Public Declare Function RegQueryValueEx Lib "advapi32.dll" Alias "RegQueryValueExA" (ByVal hKey As Long, ByVal lpValueName As String, ByVal lpReserved As Long, lpType As Long, lpData As Any, lpcbData As Long) As Long

Public Function GetSettingString(hKey As Long, strPath As String, strValue As String, Optional Default As String) As String
    Dim hCurKey As Long
    Dim lValueType As Long
    Dim strBuffer As String
    Dim lDataBufferSize As Long
    Dim intZeroPos As Integer
    Dim lRegResult As Long
    
    ' Set up default value
    If Not IsEmpty(Default) Then
      GetSettingString = Default
    Else
      GetSettingString = ""
    End If
    
    ' Open the key and get length of string
    lRegResult = RegOpenKey(hKey, strPath, hCurKey)
    lRegResult = RegQueryValueEx(hCurKey, strValue, 0&, lValueType, ByVal 0&, lDataBufferSize)
    
    If lRegResult = ERROR_SUCCESS Then
    
      If lValueType = REG_SZ Then
        ' initialise string buffer and retrieve string
        strBuffer = String(lDataBufferSize, " ")
        lRegResult = RegQueryValueEx(hCurKey, strValue, 0&, 0&, ByVal strBuffer, lDataBufferSize)
        
        ' format string
        intZeroPos = InStr(strBuffer, Chr$(0))
        If intZeroPos > 0 Then
          GetSettingString = Left$(strBuffer, intZeroPos - 1)
        Else
          GetSettingString = strBuffer
        End If
    
      End If
    
    End If
    
    lRegResult = RegCloseKey(hCurKey)
End Function

Attribute VB_Name = "UserSetting"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Public Const CountOfParams = 24

Public settingsPair(1 To CountOfParams, 1 To 2) As String

Private Function FormatString(str As String, formmater As String) As String

    Dim temp As String
    temp = ""
    formatter = Trim(formatter)
    If StrComp(formmater, "default", vbTextCompare) = 0 Then
        temp = str
    ElseIf StrComp(formmater, "Lowercase", vbTextCompare) = 0 Then
        temp = LCase(str)
    ElseIf StrComp(formmater, "Uppercase", vbTextCompare) = 0 Then
        temp = UCase(str)
    ElseIf StrComp(formmater, "Sentence Case", vbTextCompare) = 0 Then
        Dim str1 As String
        str1 = Trim(str)
        temp = UCase(Left(str1, 1)) + Right(str1, Len(str1) - 1)
    ElseIf StrComp(formmater, "Title Case", vbTextCompare) = 0 Then
        temp = str
    End If
    
    FormatString = temp

End Function

Function GetReportSettingsParam(key As String) As String
    For i = 1 To CountOfParams
        If StrComp(key, settingsPair(i, 1), vbTextCompare) = 0 Then
            GetReportSettingsParam = settingsPair(i, 2)
        End If
    Next
End Function

Private Sub BuildList(objRootElem As MSXML2.IXMLDOMElement, settingCategoryName As String, start As Integer)
    Dim queryString As String
    queryString = "//SettingCategory[@name='" + settingCategoryName + "']/Setting"
    
     Dim objSettingCategoryList As MSXML2.IXMLDOMNodeList
    Set objSettingCategoryList = objRootElem.SelectNodes(queryString)
    
    Dim objSetting As MSXML2.IXMLDOMElement
    
    i = 0
    For Each objSetting In objSettingCategoryList
        settingsPair(start + i, 1) = settingCategoryName + "." + objSetting.getAttribute("name")
        
        Dim objSettingPairList As MSXML2.IXMLDOMNodeList
        Dim querySettingPairString As String
        querySettingPairString = "./SettingPair[@name='capitalization']"
        Set objSettingPairList = objSetting.SelectNodes(querySettingPairString)
        
        Dim strValue As String
        
        Dim valueAttr As MSXML2.IXMLDOMAttribute
        Set valueAttr = objSetting.FirstChild.Attributes.getNamedItem("value")
        
        strValue = valueAttr.NodeValue
            
        If objSettingPairList.Length <> 0 Then
            Set valueAttr = objSettingPairList.Item(0).Attributes.getNamedItem("value")
            strValue = FormatString(strValue, valueAttr.NodeValue)
        End If
                
        settingsPair(start + i, 2) = strValue
        
        i = i + 1
    
    Next

End Sub

Sub LoadReportSettingsParams(strFileName As String)
    
    Dim objDoc As New MSXML2.DOMDocument
    objDoc.async = False
    objDoc.resolveExternals = False
    
    
    objDoc.Load (strFileName)
    
    Dim objRootElem As MSXML2.IXMLDOMElement
    
    Set objRootElem = objDoc.documentElement
    
    BuildList objRootElem, "Client", 1
    BuildList objRootElem, "Owner", 13
    
    Set objDoc = Nothing

End Sub


Public Sub WriteUserSetting(ts As TextStream)
    On Error GoTo ErrHandle
    Dim str As String
    Dim curSetting As Integer
    Dim sKeyPath As String
    Dim sKeyName As String
    Dim sSettingFilePath As String
    Dim pos As Long
       sKeyPath = "Software\Autodesk\LandXML Reporting\8\Settings"
    sKeyName = "SettingsFile"

    sSettingFilePath = GetSettingString(HKEY_CURRENT_USER, sKeyPath, sKeyName)
    LoadReportSettingsParams sSettingFilePath
    str = "<table border=""0"" width=""100%"">"
    ts.WriteLine (str)
    
    'add setting
    ts.WriteLine ("<tr>")
    str = "<td align=""left""><b>" + "Client:" + "</b></td>"
    ts.WriteLine (str)
    str = "<td align=""left""><b>" + "Prepared by:" + "</b></td>"
    ts.WriteLine (str)
    ts.WriteLine ("</tr>")
    
    For curSetting = 1 To 3
        ts.WriteLine ("<tr>")
        str = "<td align=""left"">" + settingsPair(curSetting, 2) + "</td>"
        ts.WriteLine (str)
        str = "<td align=""left"">" + settingsPair(curSetting + 12, 2) + "</td>"
        ts.WriteLine (str)
        ts.WriteLine ("</tr>")
    Next
    ts.WriteLine ("</table>")
    Exit Sub
ErrHandle:
    MsgBox "Read config file error."
End Sub

Attribute VB_Name = "Utilities"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Enum angleType
    TurnedPlus
    TurnedMinus
    DeflectPlus
    DeflectMinus
    Direction
End Enum
Enum rpAngDispType
    cDecDeg
    cDMS
    cGrad
    cRad
End Enum

Enum rpAngleType
    Bearing
    nAzimuth
    sAzimuth
End Enum

'Function AdjustAngle2PI(ByVal rawAngle As Double) As Double
'    pi = 4 * Atn(1)
'    Do While rawAngle >= pi * 2
'        rawAngle = rawAngle - pi * 2
'    Loop
'    Do While rawAngle < 0#
'        rawAngle = rawAngle + pi * 2
'    Loop
'    AdjustAngle2PI = rawAngle
'End Function
'
''-----------------------------------------------------------------------
''   rounds off values and returns a string.
''-----------------------------------------------------------------------
'Function RoundVal(value As Double, prec As Integer) As String
'    If Abs(value) < 10000000000# Then
'        Select Case prec
'        Case 0
'            RoundVal = Format(value, "#0")
'        Case 1
'            RoundVal = Format(value, "#0.0")
'        Case 2
'            RoundVal = Format(value, "#0.00")
'        Case 3
'            RoundVal = Format(value, "#0.000")
'        Case 4
'            RoundVal = Format(value, "#0.0000")
'        Case 5
'            RoundVal = Format(value, "#0.00000")
'        Case 6
'            RoundVal = Format(value, "#0.000000")
'        Case 7
'            RoundVal = Format(value, "#0.0000000")
'        Case 8
'            RoundVal = Format(value, "#0.00000000")
'
'        End Select
'    Else
'        RoundVal = Format(value, "0.00000000000000E+00")
'    End If
'End Function

'Function FormatAngle(dRadian As Double, AngType As rpAngDispType, Optional lRnd As Variant) As String
'
'    Dim dAng As Double
'    Dim bNeg As Boolean
'    Dim iDeg As Integer, iMin As Integer
'    Dim dSec As Double
'    Dim sDeg As String, sMin As String, sSec As String
'    Dim pi As Double
'    pi = 4 * Atn(1)
'
'    ' work with positive values, then add the neg sign after formating
'    If dRadian < 0 Then
'        bNeg = True
'    Else
'        bNeg = False
'    End If
'    dRadian = Abs(dRadian)
'
'    'calc the angle
'    Select Case AngType
'        Case cDecDeg, cDMS
'            dAng = dRadian * 180 / pi
'        Case cGrad
'            dAng = dRadian * 200 / pi
'        Case cRad
'            dAng = dRadian
'    End Select
'
'
'    ' format the return string
'    Select Case AngType
'        ' format DDD.MMSS
'        Case cDMS
'            iDeg = Int(dAng)
'            dAng = (dAng - iDeg) * 60
'
'            iMin = Int(dAng)
'            dAng = (dAng - iMin) * 60
'
'            dSec = dAng
'            ' round the seconds if necessary
'            If TypeName(lRnd) = "Integer" Then
'                Dim lRndSec As Long
'                lRndSec = lRnd - 4 ' for MMSS
'                ' don't allow precision less then a full second
'                If lRndSec < 0 Then lRndSec = 0
'                dSec = Round(dSec, lRndSec)
'            End If
'
'            ' check for values rounded up
'
'            Do While iDeg >= 360
'                iDeg = iDeg - 360
'            Loop
'
'            'get the string parts
'            sDeg = CStr(iDeg)
'            sMin = CStr(iMin)
'            sSec = CStr(dSec)
'            ' pad minutes with a leading 0 if less then 10
'            If Len(sMin) = 1 Then
'                sMin = "0" & sMin
'            End If
'            ' pad seconds with a leading 0 if less then 10
'            If dSec < 10 Then
'                sSec = "0" & sSec
'            End If
'
'            ' set the return value
'            FormatAngle = sDeg & Chr(176) & sMin & "' " & sSec & """ "
'
'        Case Else
'        ' format all others
'            If TypeName(lRnd) = "Integer" Then
'                FormatAngle = Round(dAng, CLng(lRnd))
'            Else
'                FormatAngle = CStr(dAng)
'            End If
'    End Select
'
'    If bNeg = True Then
'        FormatAngle = "-" & FormatAngle
'    End If
'
'End Function

'' convert the direction of tangent to bearing angle mode
'' Parameter: radAngle is the North-Azimuth radian format
'Public Function FormatBearingAngle(radAngle As Double, dispType As rpAngDispType, Optional lRnd As Variant) As String
'    Dim North, East, South, West
'    Dim sPrefix, sPostfix
'    Dim pi As Double
'    pi = 4 * Atn(1)
'    North = "N"
'    East = "E"
'    South = "S"
'    West = "W"
'
'    ' make sure the radAngle is in [0,2pi)
'    radAngle = AdjustAngle2PI(radAngle)
'
'
'    'Calculate
'    If radAngle <= pi / 2 Then
'        sPrefix = North
'        sPostfix = East
'    ElseIf radAngle <= pi Then
'        radAngle = pi - radAngle
'        sPrefix = South
'        sPostfix = East
'    ElseIf radAngle <= 1.5 * pi Then
'        radAngle = radAngle - pi
'        sPrefix = South
'        sPostfix = West
'    Else
'        radAngle = 2 * pi - radAngle
'        sPrefix = North
'        sPostfix = West
'    End If
'
'
'    FormatBearingAngle = sPrefix & " " & FormatAngle(radAngle, dispType, lRnd) & "" & sPostfix
'
'
''End Function
'' convert the direction of tangent to  Azimuth angle mode
'' Parameter: radAngle is the North-Azimuth radian format
'Public Function FormatAzimuthAngle(radAngle As Double, bNorth As Boolean, dispType As rpAngDispType, Optional lRnd As Variant) As String
'    Dim pi As Double
'    pi = 4 * Atn(1)
'
'    If bNorth = False Then 'South Azimuth
'        radAngle = radAngle - pi
'    End If
'
'    ' make sure the radAngle is in [0,pi)
'    radAngle = AdjustAngle2PI(radAngle)
'
'
'    FormatAzimuthAngle = FormatAngle(radAngle, dispType, lRnd)
'
'
'End Function


'-----------------------------------------------------------------------
'   calc the distance between two northing/easting points
'-----------------------------------------------------------------------
Function CalcDist(sNorth As Double, sEast As Double, eNorth As Double, eEast As Double) As Double
    
    CalcDist = (Abs(sEast - eEast) ^ 2 + Abs(sNorth - eNorth) ^ 2) ^ 0.5
    
End Function
'-----------------------------------------------------------------------
'   calc the direction in radians between two points
'-----------------------------------------------------------------------
' returned radAngle is the North-Azimuth radian format
Function CalcDirRad(sNorth As Double, sEast As Double, eNorth As Double, eEast As Double) As Double

    Dim nDiff As Double
    Dim eDiff As Double
    
    Dim pi As Double
    pi = 4 * Atn(1)
    
    nDiff = eNorth - sNorth
    eDiff = eEast - sEast
    
    If eDiff = 0# And nDiff = 0# Then
        ' the points are at the same location. This should never happend, if it does return a 0.00 direction
        CalcDirRad = 0#
        Exit Function
        
    ' return the direction for horizontal/vertical directions
    ElseIf nDiff = 0# Then
        If eDiff > 0 Then
            CalcDirRad = 0.5 * pi
        Else
            CalcDirRad = 1.5 * pi
        End If
        Exit Function
        
    ElseIf eDiff = 0# Then
        If nDiff > 0 Then
            CalcDirRad = 0#
        Else
            CalcDirRad = pi
        End If
        Exit Function
        
    End If
        
    'calc the angle from the x axis
    CalcDirRad = Atn(Abs(nDiff / eDiff))

    ' calc the direction
    If nDiff > 0 And eDiff < 0 Then
        ' 270 to 360
        CalcDirRad = 1.5 * pi + CalcDirRad
    ElseIf nDiff < 0 And eDiff < 0 Then
        ' 180 to 270
        CalcDirRad = 1.5 * pi - CalcDirRad
    ElseIf nDiff < 0 And eDiff > 0 Then
        '90 to 180
        CalcDirRad = 0.5 * pi + CalcDirRad
    Else
        '0-90
        CalcDirRad = 0.5 * pi - CalcDirRad
    End If

    
End Function

'-----------------------------------------------------------------------
'   calc the 3 point angle, return a string formated based on the current drawing setup angular settings
'-----------------------------------------------------------------------
' returned radAngle is the North-Based radian format
' Parameter: oNorth the Northing value of occupied point
' Parameter: oEast the Easting value of occupied point
' Parameter: sNorth the Northing value of Station point
' Parameter: sNorth the Easting value of Station point
' Parameter: bNorth the Northing value of backsight point
' Parameter: bNorth the Easting value of backsight point
' Return value: in [0,2PI)
Function Calc3PointAngle(oNorth As Double, oEast As Double, _
                         sNorth As Double, sEast As Double, _
                         bNorth As Double, bEast As Double, _
                         anType As angleType) As Double
    Dim dirOtoS As Double
    Dim dirOtoB As Double
    Dim pi As Double
    pi = 4 * Atn(1)
    
    If oNorth = bNorth And oEast = bEast Then
        Calc3PointAngle = 0#
        Exit Function
    End If
        
    dirOtoS = CalcDirRad(oNorth, oEast, sNorth, sEast)
    dirOtoB = CalcDirRad(oNorth, oEast, bNorth, bEast)
    
    Calc3PointAngle = dirOtoS - dirOtoB ' for TurnedPlus
    If anType = TurnedPlus Then
        Calc3PointAngle = dirOtoS - dirOtoB
    ElseIf anType = TurnedMinus Then
        Calc3PointAngle = dirOtoB - dirOtoS
    ElseIf anType = DeflectPlus Then
        Calc3PointAngle = dirOtoS + dirOtoB
    ElseIf anType = DeflectMinus Then
        Calc3PointAngle = -dirOtoS - dirOtoB
    End If
    Calc3PointAngle = AdjustAngle2PI(Calc3PointAngle)
End Function

''-----------------------------------------------------------------------
''   calc the direction between two points, return a string formated based on the current drawing setup angular settings
''-----------------------------------------------------------------------
'Function CalcDir_(sNorth As Double, sEast As Double, eNorth As Double, eEast As Double, angPrec As Integer, angDisp As rpAngDispType, angleType As rpAngleType) As String
'
'    Dim quad As Integer
'    Dim nDiff As Double
'    Dim eDiff As Double
'
'    Dim ang As Double
'
'    Dim dir As Double
'    Dim deg As Integer
'    Dim min As Integer
'    Dim sec As Integer
'    Dim sDeg As String
'    Dim sMin As String
'    Dim sSec As String
'
'    Dim sN As String
'    Dim sS As String
'    Dim sE As String
'    Dim sW As String
'
'    sN = "N" 'GetResStr(1470)
'    sS = "S" 'GetResStr(1471)
'    sE = "E" 'GetResStr(1472)
'    sW = "W" 'GetResStr(1473)
'
'    ' define pi
'    Dim pi As Double
'    pi = 4 * Atn(1)
'
'    nDiff = eNorth - sNorth
'    eDiff = eEast - sEast
'
'  '  angPrec = ImportOpts.angPrec
'    If angDisp = cDMS Then
'        angPrec = angPrec - 4
'        If angPrec < 0 Then angPrec = 0
'    End If
'
'    ' format directions exactly straight east or west
'    If nDiff = 0# Then
'        If angleType = Bearing Then
'            ' dms or grads
'            If angDisp = cDMS Then
'                sDeg = "90-00-00"
'            Else ' grads
'                sDeg = RoundVal(100, angPrec)
'            End If
'            ' format the string
'            If eDiff > 0 Then
'                CalcDir_ = sN & " " & sDeg & " " & sE
'            Else
'                CalcDir_ = sN & " " & sDeg & " " & sW
'            End If
'        ElseIf angleType = nAzimuth Then
'            ' dms or grads
'            If angDisp = cDMS Then
'                ' DMS
'                If eDiff > 0 Then
'                    CalcDir_ = "90-00-00"
'                Else
'                    CalcDir_ = "270-00-00"
'                End If
'            Else ' grads
'                If eDiff > 0 Then
'                    CalcDir_ = RoundVal(100#, angPrec)
'                Else
'                    CalcDir_ = RoundVal(300#, angPrec)
'                End If
'            End If
'        Else ' south azimuth
'            ' dms or grads
'            If angDisp = cDMS Then
'                ' DMS
'                If eDiff > 0 Then
'                    CalcDir_ = "270-00-00"
'                Else
'                    CalcDir_ = "90-00-00"
'                End If
'            Else ' grads
'                If eDiff > 0 Then
'                    CalcDir_ = RoundVal(300#, angPrec)
'                Else
'                    CalcDir_ = RoundVal(100#, angPrec)
'                End If
'            End If
'        End If
'
'    ' format directions exactly north or south
'    ElseIf eDiff = 0# Then
'        If angleType = Bearing Then
'            ' dms or grads
'            If angDisp = cDMS Then
'                sDeg = "00-00-00"
'            Else ' grads
'                sDeg = RoundVal(0#, angPrec)
'            End If
'            ' format the string
'            If nDiff > 0 Then
'                CalcDir_ = sN & " " & sDeg & " " & sE
'            Else
'                CalcDir_ = sS & " " & sDeg & " " & sE
'            End If
'        ElseIf angleType = nAzimuth Then
'            ' dms or grads
'            If angDisp = cDMS Then
'                ' DMS
'                If nDiff > 0 Then
'                    CalcDir_ = "00-00-00"
'                Else
'                    CalcDir_ = "180-00-00"
'                End If
'            Else ' grads
'                If nDiff > 0 Then
'                    CalcDir_ = RoundVal(0#, angPrec)
'                Else
'                    CalcDir_ = RoundVal(200#, angPrec)
'                End If
'            End If
'        Else ' south azimuth
'            ' dms or grads
'            If angDisp = cDMS Then
'                ' DMS
'                If nDiff > 0 Then
'                    CalcDir_ = "180-00-00"
'                Else
'                    CalcDir_ = "00-00-00"
'                End If
'            Else ' grads
'                If nDiff > 0 Then
'                    CalcDir_ = RoundVal(200#, angPrec)
'                Else
'                    CalcDir_ = RoundVal(0#, angPrec)
'                End If
'            End If
'        End If
'
'    ' format all other values
'    Else
'        If nDiff > 0 Then
'            ' it's a positive north
'            If eDiff > 0 Then
'                quad = 1
'            Else
'                quad = 4
'            End If
'        Else
'            ' it's a negative north
'            If eDiff > 0 Then
'                quad = 2
'            Else
'                quad = 3
'            End If
'        End If
'
'        'calc the angle from the x axis
'        If angleType = Bearing Then
'
'            If angDisp = cDMS Then
'                ' DMS
'                ang = Atn(Abs(nDiff / eDiff)) * 180 / pi
'
'                dir = 90 - ang
'
'                deg = Int(dir)
'
'                dir = (dir - Int(dir)) * 60
'                min = Int(dir)
'
'                dir = (dir - Int(dir)) * 60
'                sec = CInt(RoundVal(dir, 0))
'
'                ' check for values rounded to 60
'                If sec >= 60 Then
'                    sec = sec - 60
'                    min = min + 1
'                End If
'                If min >= 60 Then
'                    min = min - 60
'                    deg = deg + 1
'                End If
'                If deg >= 90 Then
'                    deg = deg - 90
'                End If
'
'                ' format the strings
'                sDeg = CStr(deg)
'                If sDeg = "0" Then sDeg = "00" & sDeg
'                sMin = CStr(min)
'                If Len(sMin) = 1 Then sMin = "0" & sMin
'                sSec = CStr(sec)
'                If Len(sSec) = 1 Then sSec = "0" & sSec
'
'                CalcDir_ = sDeg & "-" & sMin & "-" & sSec
'
'            Else
'                ' Grad
'                ang = Atn(Abs(nDiff / eDiff)) * 200 / pi
'                dir = 100 - ang
'                CalcDir_ = RoundVal(dir, angPrec)
'            End If
'
'            ' format the bearing string
'            If quad = 1 Then
'                CalcDir_ = sN & " " & CalcDir_ & " " & sE
'            ElseIf quad = 2 Then
'                 CalcDir_ = sS & " " & CalcDir_ & " " & sE
'            ElseIf quad = 3 Then
'                 CalcDir_ = sS & " " & CalcDir_ & " " & sW
'            Else
'                 CalcDir_ = sN & " " & CalcDir_ & " " & sW
'            End If
'
'        ElseIf angleType = nAzimuth Then
'
'            If ImportOpts.angDisp = cDMS Then
'                ' DMS
'                ang = Atn(Abs(nDiff / eDiff)) * 180 / pi
'
'                If quad = 1 Then
'                    dir = 90 - ang
'                ElseIf quad = 2 Then
'                    dir = 90 + ang
'                ElseIf quad = 3 Then
'                    dir = 270 - ang
'                Else
'                    dir = 270 + ang
'                End If
'
'                deg = Int(dir)
'
'                dir = (dir - Int(dir)) * 60
'                min = Int(dir)
'
'                dir = (dir - Int(dir)) * 60
'                sec = CInt(RoundVal(dir, 0))
'
'                ' check for values rounded to 60
'                If sec >= 60 Then
'                    sec = sec - 60
'                    min = min + 1
'                End If
'                If min >= 60 Then
'                    min = min - 60
'                    deg = deg + 1
'                End If
'                If deg >= 360 Then
'                    deg = deg - 90
'                End If
'
'                ' format the strings
'                sDeg = CStr(deg)
'                If sDeg = "0" Then sDeg = "00" & sDeg
'                sMin = CStr(min)
'                If Len(sMin) = 1 Then sMin = "0" & sMin
'                sSec = CStr(sec)
'                If Len(sSec) = 1 Then sSec = "0" & sSec
'
'                CalcDir_ = sDeg & "-" & sMin & "-" & sSec
'
'            Else
'                ' Grad
'                ang = Atn(Abs(nDiff / eDiff)) * 200 / pi
'                If quad = 1 Then
'                    dir = 100 - ang
'                ElseIf quad = 2 Then
'                    dir = 100 + ang
'                ElseIf quad = 3 Then
'                    dir = 300 - ang
'                Else
'                    dir = 300 + ang
'                End If
'                CalcDir_ = RoundVal(dir, angPrec)
'            End If
'
'        Else ' south azimuth
'
'            If angDisp = cDMS Then
'                ' DMS
'                ang = Atn(Abs(nDiff / eDiff)) * 180 / pi
'
'                If quad = 3 Then
'                    dir = 90 - ang
'                ElseIf quad = 4 Then
'                    dir = 90 + ang
'                ElseIf quad = 1 Then
'                    dir = 270 - ang
'                Else
'                    dir = 270 + ang
'                End If
'
'                deg = Int(dir)
'
'                dir = (dir - Int(dir)) * 60
'                min = Int(dir)
'
'                dir = (dir - Int(dir)) * 60
'                sec = CInt(RoundVal(dir, 0))
'
'                ' check for values rounded to 60
'                If sec >= 60 Then
'                    sec = sec - 60
'                    min = min + 1
'                End If
'                If min >= 60 Then
'                    min = min - 60
'                    deg = deg + 1
'                End If
'                If deg >= 360 Then
'                    deg = deg - 90
'                End If
'
'                ' format the strings
'                sDeg = CStr(deg)
'                If sDeg = "0" Then sDeg = "00" & sDeg
'                sMin = CStr(min)
'                If Len(sMin) = 1 Then sMin = "0" & sMin
'                sSec = CStr(sec)
'                If Len(sSec) = 1 Then sSec = "0" & sSec
'
'                CalcDir_ = sDeg & "-" & sMin & "-" & sSec
'
'            Else
'                ' Grad
'                ang = Atn(Abs(nDiff / eDiff)) * 200 / pi
'                If quad = 3 Then
'                    dir = 100 - ang
'                ElseIf quad = 4 Then
'                    dir = 100 + ang
'                ElseIf quad = 1 Then
'                    dir = 300 - ang
'                Else
'                    dir = 300 + ang
'                End If
'                CalcDir_ = RoundVal(dir, angPrec)
'            End If
'        End If
'    End If
'
'End Function
'Function Get2PointDirData(sNorth As Double, sEast As Double, eNorth As Double, eEast As Double, angPrec As Integer, angDisp As rpAngDispType, angleType As rpAngleType) As String
'    Dim radAngle As Double
'    Dim sResult As String
'    ' get the radangle direction first
'    radAngle = CalcDirRad(sNorth, sEast, eNorth, eEast)
'
'    Select Case angleType
'        Case Bearing
'            sResult = FormatBearingAngle(radAngle, angDisp, angPrec)
'        Case nAzimuth
'            sResult = FormatAzimuthAngle(radAngle, True, angDisp, angPrec)
'        Case Else 'sAzimuth
'            sResult = FormatAzimuthAngle(radAngle, False, angDisp, angPrec)
'    End Select
'    Get2PointDirData = sResult
'End Function
