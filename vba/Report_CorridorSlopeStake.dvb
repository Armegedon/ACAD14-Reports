Attribute VB_Name = "Application"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
Public g_oCivilApp As AeccApplication
Public g_oAeccDb As AeccDatabase
Public g_oCivilRoadwayApp As AeccRoadwayApplication
Public g_oRoadwayDocument As AeccRoadwayDocument


Private Const sAppName = "AeccXUiLand.AeccApplication." + MODVER
Private Const sRoadwayAppName = "AeccXUiRoadway.AeccRoadwayApplication." + MODVER

'
' Start Civil 3D, create document and database objects.
'


Public Function InitCooridorApp() As Boolean
    Dim oApp As AcadApplication
    Set oApp = ThisDrawing.Application
    
    Set g_oCivilRoadwayApp = oApp.GetInterfaceObject(sRoadwayAppName)
    If g_oCivilRoadwayApp Is Nothing Then
        MsgBox "Error creating " & sRoadwayAppName & ", exit."
        InitCooridorApp = False
        Exit Function
    End If
    Set g_oRoadwayDocument = g_oCivilRoadwayApp.ActiveDocument
    Set g_oAeccDb = g_oCivilRoadwayApp.ActiveDocument.Database
    InitCooridorApp = True
End Function

Attribute VB_Name = "CBaseline"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Public mObject As AeccBaseline
Public mSampleLineGroups As Dictionary
Public mLinkCodesGroups As Dictionary

Private Sub Class_Initialize()
    Set mSampleLineGroups = New Dictionary
    Set mLinkCodesGroups = New Dictionary
End Sub

Private Sub Class_Terminate()
    Set mObject = Nothing
End Sub

Attribute VB_Name = "CCorridor"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Public mObject As AeccCorridor
Public mBaselines As Dictionary

Private Sub Class_Initialize()
    Set mBaselines = New Dictionary
End Sub

Private Sub Class_Terminate()
    Set mObject = Nothing
End Sub

Attribute VB_Name = "CFileDialog"
Attribute VB_Base = "0{FCFB3D2A-A0FA-1068-A738-08002B3371B5}"
Attribute VB_GlobalNameSpace = False
Attribute VB_Creatable = False
Attribute VB_PredeclaredId = False
Attribute VB_Exposed = True
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

' Class       : CFileDialog
' Description : Class for displaying the File Open/Save Common Dialog.
' Source      : Total VB SourceBook 5
' Update      : Code Service Pack 1

Private Type OPENFILENAME
  lStructSize As Long
  hwndOwner As Long
  hInstance As Long
  lpstrFilter As String
  lpstrCustomFilter As String
  nMaxCustFilter As Long
  nFilterIndex As Long
  lpstrFile As String
  nMaxFile As Long
  lpstrFileTitle As String
  nMaxFileTitle As Long
  lpstrInitialDir As String
  lpstrTitle As String
  Flags As Long
  nFileOffset As Integer
  nFileExtension As Integer
  lpstrDefExt As String
  lCustData As Long
  lpfnHook As Long
  lpTemplateName As String
End Type

Private Declare Function GetOpenFileName _
  Lib "comdlg32.dll" _
  Alias "GetOpenFileNameA" _
  (pOpenfilename As OPENFILENAME) _
  As Long

Private Declare Function GetSaveFileName _
  Lib "comdlg32.dll" _
  Alias "GetSaveFileNameA" _
  (pOpenfilename As OPENFILENAME) _
  As Long

Private m_strDefaultExt As String
Private m_strDialogTitle As String
Private m_strFileName As String
Private m_strFileTitle As String
Private m_strInitialDir As String
Private m_strFilter As String
Private m_intFilterIndex As Integer
Private m_eFlags As Variant
Private m_intMaxFileSize As Integer
Private m_lnghWndParent As Long

Private Const cintMaxFileLength As Integer = 260

Dim EnumFilFlags
Dim FleReadOnly
Dim FleOverWritePrompt
Dim FleHideReadOnly
Dim FleNoChangeDir
Dim FleShowHelp
Dim FleEnableHook
Dim FleEnableTemplate
Dim FleEnableTemplateHandle
Dim FleNoValidate
Dim FleAllowMultiSelect
Dim FleExtensionDifferent
Dim FlePathMustExist
Dim FleFileMustExist
Dim FleCreatePrompt
Dim FleShareAware
Dim FleNoReadOnlyReturn
Dim FleNoTestFileCreate
Dim FleNoNetworkButton
Dim FleExplorer
Dim FleLongnames

Public Property Get DefaultExt() As String
  ' Returns: The default extension
  ' Source: Total VB SourceBook 5

  DefaultExt = m_strDefaultExt

End Property

Public Property Let DefaultExt(ByVal strValue As String)
  ' strValue: Set the default extension used for a filename
  ' Source: Total VB SourceBook 5

  m_strDefaultExt = strValue

End Property

Public Property Get DialogTitle() As String
  ' Returns: The title displayed in the dialog
  ' Source: Total VB SourceBook 5

  DialogTitle = m_strDialogTitle

End Property

Public Property Let DialogTitle(ByVal strValue As String)
  ' strValue: Set the title displayed in the dialog
  ' Source: Total VB SourceBook 5

  m_strDialogTitle = strValue

End Property

Public Property Get FileName() As String
  ' Returns: The path and filename
  ' Source: Total VB SourceBook 5

  FileName = m_strFileName

End Property

Public Property Let FileName(ByVal strValue As String)
  ' strValue: Set the filename
  ' Source: Total VB SourceBook 5

  m_strFileName = strValue

End Property

Public Property Get FileTitle() As String
  ' Returns: The filename without the path
  ' Source: Total VB SourceBook 5

  FileTitle = m_strFileTitle

End Property

Public Property Let FileTitle(ByVal strValue As String)
  ' strValue: Set the file title
  ' Source: Total VB SourceBook 5

  m_strFileTitle = strValue

End Property

Public Property Get Filter() As String
  ' Returns: The filter string
  ' Source: Total VB SourceBook 5

  Filter = m_strFilter

End Property

Public Property Let Filter(ByVal strValue As String)
  ' strValue: Set the filter string
  ' Source: Total VB SourceBook 5

  m_strFilter = strValue

End Property

Public Property Get FilterIndex() As Integer
  ' Returns: The index of the filter to display
  ' Source: Total VB SourceBook 5

  FilterIndex = m_intFilterIndex

End Property

Public Property Let FilterIndex(ByVal intValue As Integer)
  ' Set the index of the filter to display
  ' Source: Total VB SourceBook 5

  m_intFilterIndex = intValue

End Property

Public Property Get Flags() As Variant
  ' Returns: The flags
  ' Source: Total VB SourceBook 5

  Flags = m_eFlags

End Property

Public Property Let Flags(ByVal eValue As Variant)
  ' eValue: Set the flags
  ' Source: Total VB SourceBook 5

  m_eFlags = eValue

End Property

Public Property Get hWndParent() As Long
  ' Returns: The parent hwnd
  ' Source: Total VB SourceBook 5

  hWndParent = m_lnghWndParent

End Property

Public Property Let hWndParent(ByVal lngValue As Long)
  ' lngValue: Set the parent hwnd
  ' Source: Total VB SourceBook 5

  m_lnghWndParent = lngValue

End Property

Public Property Get InitialDir() As String
  ' Returns: The current value of InitialDir
  ' Source : Total VB SourceBook 5
  ' Update : Code Service Pack 1

  InitialDir = m_strInitialDir

End Property

Public Property Let InitialDir(ByVal strValue As String)
  ' strValue: Set to the path where the dialog should open
  ' Source  : Total VB SourceBook 5
  ' Update  : Code Service Pack 1

  m_strInitialDir = strValue

End Property

Public Property Get MaxFileSize() As Integer
  ' Returns: The maximum length of the filename
  ' Source: Total VB SourceBook 5

  MaxFileSize = m_intMaxFileSize

End Property

Public Property Let MaxFileSize(ByVal intValue As Integer)
  ' intValue: Set the maximum length of the filename
  ' Source: Total VB SourceBook 5

  m_intMaxFileSize = intValue

End Property

Public Function Show(fOpen As Boolean) As Boolean
  ' Comments  : This procedure displays the file Open/Save common dialog
  ' Parameters: fOpen - Determines if the Open or Save dialog is displayed.
  ' Returns   : False if cancel selected, true otherwise.
  ' Source    : Total VB SourceBook 5
  ' Update    : Code Service Pack 1
  '

  Dim of As OPENFILENAME
  Dim strChar As String * 1
  Dim intCounter As Integer
  Dim strtemp As String
  
  On Error GoTo PROC_ERR
  
  ' Initialize the OPENFILENAME type
  of.lpstrTitle = m_strDialogTitle & ""
  of.Flags = m_eFlags
  of.lpstrDefExt = m_strDefaultExt & ""
  of.lStructSize = LenB(of)
  of.lpstrFilter = m_strFilter & "||"
  of.nFilterIndex = m_intFilterIndex
  
  ' To make Windows-style filter, replace pipes with nulls
  For intCounter = 1 To Len(m_strFilter)
    strChar = Mid$(m_strFilter, intCounter, 1)
    If strChar = "|" Then
      strtemp = strtemp & vbNullChar
    Else
      strtemp = strtemp & strChar
    End If
  Next
  
  ' Put double null at end
  strtemp = strtemp & vbNullChar & vbNullChar
  of.lpstrFilter = strtemp
  
  ' Pad file and file title buffers to maximum path length
  strtemp = m_strFileName & String$(cintMaxFileLength - Len(m_strFileName), 0)
  of.lpstrFile = strtemp
  of.nMaxFile = cintMaxFileLength
  
  strtemp = m_strFileTitle & String$(cintMaxFileLength - Len(m_strFileTitle), 0)
  of.lpstrFileTitle = strtemp
  of.lpstrInitialDir = m_strInitialDir
  of.nMaxFileTitle = cintMaxFileLength
  of.hwndOwner = m_lnghWndParent
  
  ' If fOpen is true, show the Open file dialog, otherwise show the Save dialog
  If fOpen Then
    If GetOpenFileName(of) Then
      Show = True
      ' Assign property variables to appropriate values
      m_strFileName = TrimNulls(of.lpstrFile)
      m_strFileTitle = TrimNulls(of.lpstrFileTitle)
    Else
      Show = False
    End If
  Else
    If GetSaveFileName(of) Then
      Show = True
      ' Assign property variables to appropriate values
      m_strFileName = TrimNulls(of.lpstrFile)
      m_strFileTitle = TrimNulls(of.lpstrFileTitle)
    Else
      Show = False
    End If
  End If
  
PROC_EXIT:
  Exit Function
  
PROC_ERR:
  MsgBox "Error: " & Err.Number & ". " & Err.Description, , _
  "Show"
  Resume PROC_EXIT

End Function

Private Function TrimNulls(ByVal strIn As String) As String
  ' Comments  : Returns the passed string terminated at the first null
  ' Parameters: strIn - Value to parse
  ' Returns   : Parsed string
  ' Source    : Total VB SourceBook 5
  '
  Dim intPos As Integer
  
  On Error GoTo PROC_ERR
    
  intPos = InStr(strIn, vbNullChar)
  
  If intPos = 0 Then
    ' No nulls in the string, just return it as is
    TrimNulls = strIn
  Else
    If intPos = 1 Then
      ' If the null character is at the first position, the
      ' entire string is a null string, so return a zero-length string
      TrimNulls = ""
    Else
      ' Not at the first position, so return the contents up
      ' to the occurrence of the null character
      TrimNulls = Left$(strIn, intPos - 1)
    End If
  End If
    
PROC_EXIT:
  Exit Function
  
PROC_ERR:
  MsgBox "Error: " & Err.Number & ". " & Err.Description, , _
    "TrimNulls"
  Resume PROC_EXIT
    
End Function

Private Sub Class_Initialize()
  FleReadOnly = &H1
  FleOverWritePrompt = &H2
  FleHideReadOnly = &H4
  FleNoChangeDir = &H8
  FleShowHelp = &H10
  FleEnableHook = &H20
  FleEnableTemplate = &H40
  FleEnableTemplateHandle = &H80
  FleNoValidate = &H100
  FleAllowMultiSelect = &H200
  FleExtensionDifferent = &H400
  FlePathMustExist = &H800
  FleFileMustExist = &H1000
  FleCreatePrompt = &H2000
  FleShareAware = &H4000
  FleNoReadOnlyReturn = &H8000
  FleNoTestFileCreate = &H10000
  FleNoNetworkButton = &H20000
  FleExplorer = &H80000
  FleLongnames = &H200000
End Sub

Attribute VB_Name = "CLinkCodes"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Public mCodeName As String
Public mAdded As Boolean
Private Sub Class_Initialize()
    mAdded = False
End Sub

Attribute VB_Name = "CSampleLineGroup"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.

Public mObject As AeccSampleLineGroup

Private Sub Class_Terminate()
    Set mObject = Nothing
End Sub

Attribute VB_Name = "DataExtractor"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit

Public Const nStartStationIndex = 0
Public Const nStartNorthingIndex = 1
Public Const nStartEastingIndex = 2
Public Const nEndStationIndex = 3
Public Const nEndNorthingIndex = 4
Public Const nEndEastingIndex = 5
Public Const nLengthValueIndex = 6
Public Const nDirectionIndex = 7
Public Const nLastIndex = nDirectionIndex

Public Const nLeftIndex = 0
Public Const nRightIndex = 1
Public Const nLeftEndIndex = 2
Public Const nRightEndIndex = 3

Public Const nCodeIndex = 0
Public Const nOffsetIndex = 1
Public Const nElevIndex = 2
Public Const nSlopeIndex = 3

Public g_oSlopeStakeData As New Dictionary

Function FormatCoordSettings(ByVal dDis As Double) As String
    Dim oCoordSettings As AeccSettingsCoordinate
    Set oCoordSettings = g_oAeccDb.Settings.AlignmentSettings.AmbientSettings.CoordinateSettings
        
    FormatCoordSettings = FormatDistance(dDis, oCoordSettings.Unit.Value, oCoordSettings.Precision.Value, _
                oCoordSettings.Rounding.Value, oCoordSettings.Sign.Value)
End Function
Function FormatDistSettings(ByVal dDis As Double) As String
    Dim oDistSettings As AeccSettingsDistance
    Set oDistSettings = g_oAeccDb.Settings.AlignmentSettings.AmbientSettings.DistanceSettings
    
    FormatDistSettings = FormatDistance(dDis, oDistSettings.Unit.Value, oDistSettings.Precision.Value, _
                oDistSettings.Rounding.Value, oDistSettings.Sign.Value)
End Function
Function FormatDirSettings(ByVal dDirection As Double) As String
    Dim oDirSettings As AeccSettingsDirection
    Set oDirSettings = g_oAeccDb.Settings.AlignmentSettings.AmbientSettings.DirectionSettings
    
    FormatDirSettings = FormatDirection(dDirection, oDirSettings.Unit.Value, oDirSettings.Precision.Value, _
                                        oDirSettings.Rounding.Value, oDirSettings.Format.Value, _
                                        oDirSettings.Direction.Value, oDirSettings.Capitalization.Value, _
                                        oDirSettings.Sign.Value, oDirSettings.MeasurementType.Value, oDirSettings.BearingQuadrant)
End Function

Function FormatElevSettings(ByVal dDis As Double) As String
    Dim oElevSettings As AeccSettingsElevation
    Set oElevSettings = g_oAeccDb.Settings.AlignmentSettings.AmbientSettings.ElevationSettings
    
    FormatElevSettings = FormatDistance(dDis, oElevSettings.Unit.Value, oElevSettings.Precision.Value, _
                oElevSettings.Rounding.Value, oElevSettings.Sign.Value)
End Function


Public Function ExtractData(oCorridor As AeccCorridor, oBaseline As AeccBaseline, oSampleLineGroups As AeccSampleLineGroup, stationStart As Double, stationEnd As Double, sCodeName As String) As Boolean
    Dim oSampleLine As AeccSampleLine
    Dim oLinks As AeccCalculatedLinks
    Dim curStation As Double
    Dim datumElevation As Double
    Dim cLeftDatas As Dictionary
    Dim cRightDatas As Dictionary
    ExtractData = False

    g_oSlopeStakeData.removeAll
    
    Dim dLastStation As Double
    dLastStation = -1122323.323

    For Each oSampleLine In oSampleLineGroups.SampleLines
        Dim aDataBySta(0 To 3) As Variant

        Dim oLink As AeccCalculatedLink
        Dim leftOff As Double
        Dim leftElev As Double
        Dim rightOff As Double
        Dim rightElev As Double
        Dim dLastLeftOff As Double
        Dim dLastLeftElev As Double
        Dim dLastRightOff As Double
        Dim dLastRightElev As Double
        curStation = oSampleLine.Station
        curStation = GetRawStation(oSampleLineGroups.Parent.GetStationStringWithEquations(curStation))
        If curStation < stationStart Or curStation > stationEnd Then
            GoTo ErrHandler
        End If
        If curStation - dLastStation < 0.001 Then
            GoTo ErrHandler
        Else
            dLastStation = curStation
        End If
        
        datumElevation = oBaseline.profile.ElevationAt(curStation)
        On Error GoTo ErrHandler
        Set oLinks = oBaseline.AppliedAssembly(curStation).GetLinksByCode(sCodeName)
        Set cLeftDatas = New Dictionary
        Set cRightDatas = New Dictionary
        leftElev = datumElevation
        leftOff = 0
        rightElev = datumElevation
        rightOff = 0
        For Each oLink In oLinks
            Dim oPoint As AeccCalculatedPoint
            Dim vx As Variant
            Dim off As Double
            For Each oPoint In oLink.CalculatedPoints
                Dim oDataArr(0 To 3)

                vx = oPoint.GetStationOffsetElevationToBaseline
                off = vx(1)
                If off < 0 Then
                    If Not cLeftDatas.Exists(off) Then
                        dLastLeftOff = leftOff
                        dLastLeftElev = leftElev
                        leftOff = off: leftElev = vx(2) + datumElevation
                        oDataArr(nOffsetIndex) = leftOff
                        oDataArr(nElevIndex) = leftElev
                        oDataArr(nCodeIndex) = oPoint.CorridorCodes(0)
                        oDataArr(nSlopeIndex) = GetSlopeData(leftOff, dLastLeftOff, leftElev, dLastLeftElev)
                        dLastLeftElev = leftElev
                        cLeftDatas.Add leftOff, oDataArr
                End If
                Else
                    If Not cRightDatas.Exists(off) Then
                        dLastRightOff = rightOff
                        dLastRightElev = rightElev
                        rightOff = off: rightElev = vx(2) + datumElevation
                        oDataArr(nOffsetIndex) = rightOff
                        oDataArr(nElevIndex) = rightElev
                        oDataArr(nCodeIndex) = oPoint.CorridorCodes(0)
                        oDataArr(nSlopeIndex) = GetSlopeData(rightOff, dLastRightOff, rightElev, dLastRightElev)
                        cRightDatas.Add rightOff, oDataArr
                    End If
                End If

            Next


        Next

        'now sort the keys
        Dim varLeftKeyArray As Variant
        varLeftKeyArray = cLeftDatas.Keys
        quicksort varLeftKeyArray
        Dim varRightKeyArray As Variant
        varRightKeyArray = cRightDatas.Keys
        quicksort (varRightKeyArray)

        Dim cNewLeftDatas
        Dim cNewRightDatas
        Set cNewLeftDatas = New Dictionary
        Set cNewRightDatas = New Dictionary

        Dim dPreKey As Variant
        Dim dKey As Variant
        Dim arrLeftData As Variant
        Dim arrRightData As Variant
        Dim iIndex As Integer
        dPreKey = 1#
        Dim arrLeftDataStr(0 To 3) As String
        Dim arrRightDataStr(0 To 3) As String
        For iIndex = UBound(varLeftKeyArray) To 0 Step -1
            dKey = varLeftKeyArray(iIndex)
            If Abs(dKey - dPreKey) > 0.01 Then
                dLastLeftOff = leftOff
                dLastLeftElev = leftElev
                arrLeftData = cLeftDatas.item(dKey)
                arrLeftDataStr(nOffsetIndex) = FormatDistSettings(arrLeftData(nOffsetIndex))
                arrLeftDataStr(nElevIndex) = FormatElevSettings(arrLeftData(nElevIndex))
                arrLeftDataStr(nCodeIndex) = arrLeftData(nCodeIndex)
                arrLeftDataStr(nSlopeIndex) = arrLeftData(nSlopeIndex)
                cNewLeftDatas.Add dKey, arrLeftDataStr
                leftOff = arrLeftData(nOffsetIndex)
                leftElev = arrLeftData(nElevIndex)
            End If
            dPreKey = dKey
        Next iIndex
        dPreKey = -1#
        For Each dKey In varRightKeyArray
            If Abs(dKey - dPreKey) > 0.01 Then
                dLastRightOff = rightOff
                dLastRightElev = rightElev
                arrRightData = cRightDatas.item(dKey)
                arrRightDataStr(nOffsetIndex) = FormatDistSettings(arrRightData(nOffsetIndex))
                arrRightDataStr(nElevIndex) = FormatElevSettings(arrRightData(nElevIndex))
                arrRightDataStr(nCodeIndex) = arrRightData(nCodeIndex)
                arrRightDataStr(nSlopeIndex) = arrRightData(nSlopeIndex)
                cNewRightDatas.Add dKey, arrRightDataStr
                rightOff = arrRightData(nOffsetIndex)
                rightElev = arrRightData(nElevIndex)
            End If
            dPreKey = dKey
        Next


        aDataBySta(nLeftEndIndex) = GetEndColumInfo(dLastLeftOff, dLastLeftElev, leftOff, leftElev)
        aDataBySta(nRightEndIndex) = GetEndColumInfo(dLastRightOff, dLastRightElev, rightOff, rightElev)
        Set aDataBySta(nLeftIndex) = cNewLeftDatas
        Set aDataBySta(nRightIndex) = cNewRightDatas

        If False = g_oSlopeStakeData.Exists(curStation) Then
            g_oSlopeStakeData.Add curStation, aDataBySta
        End If
ErrHandler:
        If Err.Number <> 0 Then
            Resume NextLoop
        End If
NextLoop:
    Next
    
    
    ExtractData = True
    
End Function


Private Function GetSlopeData(curOff As Double, lastOff As Double, curElev As Double, lastElev As Double) As String
    Dim deltaX As Double
    Dim deltaY As Double
    Dim slope As Double
    Const percent2Slope = 0.1
    deltaX = Abs(curOff - lastOff)
    deltaY = curElev - lastElev
    
    If (deltaX <> 0) Then
        slope = deltaY / deltaX
        If (Abs(slope) <= percent2Slope) Then
            GetSlopeData = VBA.Format(slope, "percent")
        Else
            GetSlopeData = "1:" & VBA.Format(slope, "0.00")
        End If
    Else
        GetSlopeData = VBA.Format(0, "0.00")
    End If
   

End Function

Private Function GetEndColumInfo(last2Off As Double, last2Elev As Double, lastOff As Double, lastElev As Double) As Variant
    Dim tmpArr(0 To 2)
    Dim deltaY As Double
    
    deltaY = lastElev - last2Elev
    If deltaY < 0 Then
        tmpArr(0) = "F" & VBA.Format(Abs(deltaY), "0.00")
    Else
        tmpArr(0) = "C" & VBA.Format(deltaY, "0.00")
    End If
    tmpArr(1) = "@" & VBA.Format(Abs(lastOff - last2Off), "0.00")
    tmpArr(2) = GetSlopeData(last2Off, lastOff, last2Elev, lastElev)

    GetEndColumInfo = tmpArr
End Function

Attribute VB_Name = "ReportForm_CorridorSlopeStake"
Attribute VB_Base = "0{437A10E4-DA9C-44AD-B9D6-C4919BB82FE8}{32FD6FAC-2E6C-4D5D-B73C-F6348E5D72A1}"
Attribute VB_GlobalNameSpace = False
Attribute VB_Creatable = False
Attribute VB_PredeclaredId = True
Attribute VB_Exposed = False
Attribute VB_TemplateDerived = False
Attribute VB_Customizable = False
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'
Option Explicit
'
Private Type ItemStationInfo
    index As Long
    oSampleLineGroup As AeccSampleLineGroup '
    startStation As Double
    endStation As Double
    curStartStation As Double
    curEndStation As Double
End Type

Private g_StationInfo As ItemStationInfo

Private g_sFileName As String
Private g_reportFileName As String

Private g_Corridors As New Dictionary

Private Const nNameIndex = 0
Private Const nAlignmentIndex = 1
Private Const nSampleLineGroup = 2
Private Const nLinkCodes = 3
Private Const nStationStartIndex = 4
Private Const nStationEndIndex = 5
Private Const nLastIndex = nStationEndIndex

Private sCaptionArr() As String


Private Sub DeleteButton_Click()
    Dim i As Long
    Dim item As ListItem
    Dim colItems As ListItems
    Dim oCorridorInfo As CCorridor
    Dim oBaselineInfo As CBaseline
    Dim oSampleLineGroupInfo As CSampleLineGroup
    Dim oLinkCodeInfo As CLinkCodes
    
    Set colItems = ListView.ListItems
    For i = 1 To colItems.count Step 1
        Set item = colItems.item(i)
        If item.Selected = True Then
            Set oCorridorInfo = g_Corridors.item(item.Text)
            Set oBaselineInfo = oCorridorInfo.mBaselines.item(item.SubItems(nAlignmentIndex))
            Set oSampleLineGroupInfo = oBaselineInfo.mSampleLineGroups.item(item.SubItems(nSampleLineGroup))
            Set oLinkCodeInfo = oBaselineInfo.mLinkCodesGroups.item(item.SubItems(nLinkCodes))
            oLinkCodeInfo.mAdded = False
            If item.index = g_StationInfo.index Then
                StartStaEdit.Enabled = False
                StartStaEdit.Value = ""
                EndStaEdit.Enabled = False
                EndStaEdit.Value = ""
            End If
            colItems.Remove i
            i = i - 1
        End If
        If i = colItems.count Then
            Exit For
        End If
    Next i
     
  
End Sub
Private Sub AddButton_Click()
    If Combo_LineGroup.ListCount = 0 Or Combo_Link.ListCount = 0 Then
        Exit Sub
    End If
    
    Dim oSampleLineGroupInfo As CSampleLineGroup
    Dim oSampleLineGroup As AeccSampleLineGroup
    Set oSampleLineGroupInfo = FindSampleLineGroupInfo(Combo_Corridor.SelText, _
                                               Combo_Align.SelText, _
                                               Combo_LineGroup.SelText)
    Set oSampleLineGroup = oSampleLineGroupInfo.mObject
    
    Dim oLinkCodesInfo As CLinkCodes
    Dim sCodeName As String
    Set oLinkCodesInfo = FindLinkCodesInfo(Combo_Corridor.SelText, _
                                    Combo_Align.SelText, _
                                    Combo_Link.SelText)
    sCodeName = oLinkCodesInfo.mCodeName
    
    If oLinkCodesInfo.mAdded = False Then
        Dim item As ListItem
        Dim dStartStation As Double, dEndStation As Double
        Call StartStationOfSampleLineGroup(oSampleLineGroup, dStartStation, dEndStation)
        
        Set item = ListView.ListItems.Add(, , Combo_Corridor.SelText)
        item.SubItems(nAlignmentIndex) = Combo_Align.SelText
        item.SubItems(nSampleLineGroup) = Combo_LineGroup.SelText
        item.SubItems(nLinkCodes) = Combo_Link.SelText
        item.SubItems(nStationStartIndex) = oSampleLineGroup.Parent.GetStationStringWithEquations(dStartStation)
        item.SubItems(nStationEndIndex) = oSampleLineGroup.Parent.GetStationStringWithEquations(dEndStation)
        oLinkCodesInfo.mAdded = True
    Else
        MsgBox "The component has already been to be reported."
    End If
    
End Sub

Private Sub Combo_LineGroup_Change()
    Dim oSampleLineGroupInfo As CSampleLineGroup
    If Combo_LineGroup.ListCount = 0 Then
        Exit Sub
    End If
    Set oSampleLineGroupInfo = FindSampleLineGroupInfo(Combo_Corridor.SelText, _
                                               Combo_Align.SelText, _
                                               Combo_LineGroup.SelText)
    If oSampleLineGroupInfo.mObject.SampleLines.count = 0 Then
        AddButton.Enabled = False
        MsgBox "The Selected Sample Line Group has no Sample line."
    Else
        AddButton.Enabled = True
    End If
        
  
End Sub

Private Sub Combo_Align_Change()
    Dim oCorridorInfo As CCorridor
    Dim oBaselineInfo As CBaseline
    Dim sSampleLineGroupName
    Dim sLinkCodeName
 
        
    If Combo_Align.ListCount = 0 Then
        Exit Sub
    End If
    
    Set oCorridorInfo = g_Corridors.item(Combo_Corridor.SelText)
    Set oBaselineInfo = oCorridorInfo.mBaselines.item(Combo_Align.SelText)
    
    Combo_LineGroup.Clear
    For Each sSampleLineGroupName In oBaselineInfo.mSampleLineGroups.Keys
        Combo_LineGroup.AddItem sSampleLineGroupName
    Next
    
    Combo_Link.Clear
    For Each sLinkCodeName In oBaselineInfo.mLinkCodesGroups.Keys
        Combo_Link.AddItem sLinkCodeName
    Next
   
    If Combo_LineGroup.ListCount > 0 Then
        Combo_LineGroup.ListIndex = 0
    Else
        AddButton.Enabled = False
        MsgBox "No Sample Line Group available in select alignment."
    End If
    
    If Combo_Link.ListCount > 0 Then
        Combo_Link.ListIndex = 0
    Else
        AddButton.Enabled = False
        MsgBox "No Link available in select alignment."
    End If
End Sub

Private Sub Combo_Corridor_Change()
    Dim oCorridorInfo As CCorridor
    Dim sAlignmentName
    
    If Combo_Corridor.ListCount = 0 Then
        Exit Sub
    End If
    
    Set oCorridorInfo = g_Corridors.item(Combo_Corridor.SelText)
    Combo_Align.Clear
    For Each sAlignmentName In oCorridorInfo.mBaselines.Keys
        Combo_Align.AddItem sAlignmentName
    Next
    
    If Combo_Align.ListCount > 0 Then
        Combo_Align.ListIndex = 0
    Else
        AddButton.Enabled = False
        MsgBox "No Alignment available."
    End If
End Sub



Private Sub HelpButton_Click()
    ReportsHH_hWnd = ReportsHtmlHelp(0, getReportsHelpFile, HH_HELP_CONTEXT, IDH_AECC_REPORTS_CREATE_SLOPE_GRADE_REPORT)
End Sub

Private Sub SelectButton_Click()
    On Error GoTo Cancel
    Dim oEntity As Object
    Dim pt(2) As Double
    Me.Hide
    ThisDrawing.Utility.GetEntity oEntity, pt, "Select a Corridor."
    Do While Not TypeOf oEntity Is AeccCorridor
        ThisDrawing.Utility.GetEntity oEntity, pt, "Please select a Corridor."
    Loop
    Combo_Corridor.Text = oEntity.Name
Cancel:
    Me.Show
End Sub

' Initialize the main dialog
Private Sub UserForm_Initialize()
    Dim tempPath As String
    Dim oCorridors As AeccCorridors
    Dim oCorridor As AeccCorridor
    Dim oCorridorInfo As CCorridor
    g_sFileName = g_oCivilRoadwayApp.Path

    tempPath = Environ("temp")
    g_reportFileName = tempPath & "\civilreport.html"


    ReportFileNameEdit.Text = g_reportFileName

    'initial Select report Components

    g_Corridors.removeAll
    On Error GoTo NoCorridor
    Set oCorridors = g_oRoadwayDocument.Corridors
    On Error GoTo 0
    For Each oCorridor In oCorridors
        If g_Corridors.Exists(oCorridor.Name) = False Then
            Set oCorridorInfo = New CCorridor
            BuildCorridorInfo oCorridor, oCorridorInfo
            g_Corridors.Add oCorridor.Name, oCorridorInfo
            Combo_Corridor.AddItem oCorridor.Name
        End If
    Next
    If g_Corridors.count > 0 Then
        Combo_Corridor.ListIndex = 0
    Else
        AddButton.Enabled = False
        GoTo NoCorridor
    End If
    

    ' progress bar settings
    ProgressBar.Min = 0
    ProgressBar.Max = 100
    ProgressBar.Visible = False
    progressBarLabel.Visible = False

    
    ' Get Captions
    GetCaptions
    
    ' list view grid setup
    ' setup columns
    
    Call ListView.ColumnHeaders.Add(1, , sCaptionArr(nNameIndex), 100, lvwColumnLeft)
    Call ListView.ColumnHeaders.Add(2, , sCaptionArr(nAlignmentIndex), 80, lvwColumnLeft)
    Call ListView.ColumnHeaders.Add(3, , sCaptionArr(nSampleLineGroup), 100, lvwColumnLeft)
    Call ListView.ColumnHeaders.Add(4, , sCaptionArr(nLinkCodes), 80, lvwColumnLeft)
    Call ListView.ColumnHeaders.Add(5, , sCaptionArr(nStationStartIndex), 80, lvwColumnLeft)
    Call ListView.ColumnHeaders.Add(6, , sCaptionArr(nStationEndIndex), 80, lvwColumnLeft)

    StartStaEdit.Enabled = False
    EndStaEdit.Enabled = False
    Exit Sub
NoCorridor:
    MsgBox "No corridors in " & ThisDrawing.Name & " exist."
    End
End Sub


' Do the real work of gnerating the report here
Private Sub ExecuteButton_Click()
    Dim t, pbarInc, cCount As Integer
    Dim stat As Boolean
    Dim curListItem As ListItem
    Dim exeStr As String
    Dim inStartStation As Double
    Dim inEndStation As Double
    Dim oCorridorInfo As CCorridor
    Dim oBaselineInfo As CBaseline
    Dim oSampleLineGroupInfo As CSampleLineGroup
    Dim oLinkCodesInfo As CLinkCodes

    If ListView.ListItems.count = 0 Then
        Exit Sub
    End If

    For t = 1 To ListView.ListItems.count
        If ListView.ListItems(t).Checked = True Then
            cCount = cCount + 1
            pbarInc = 80 / cCount
        End If
    Next

    ProgressBar.Value = 0
    
    progressBarLabel.Enabled = False
    progressBarLabel.Enabled = True

    progressBarLabel.Visible = True
    ProgressBar.Visible = True

    Call WriteReportHeader(g_reportFileName)

    'update progress bar
    ProgressBar.Value = 10

    For t = 1 To ListView.ListItems.count
        Set curListItem = ListView.ListItems(t)
        inStartStation = GetRawStation(curListItem.SubItems(nStationStartIndex))
        inEndStation = GetRawStation(curListItem.SubItems(nStationEndIndex))
        Set oCorridorInfo = g_Corridors.item(curListItem.Text)
        Set oBaselineInfo = oCorridorInfo.mBaselines.item(curListItem.SubItems(nAlignmentIndex))
        Set oSampleLineGroupInfo = oBaselineInfo.mSampleLineGroups.item(curListItem.SubItems(nSampleLineGroup))
        Set oLinkCodesInfo = oBaselineInfo.mLinkCodesGroups.item(curListItem.SubItems(nLinkCodes))
        stat = AppendReport(oCorridorInfo.mObject, oBaselineInfo.mObject, oSampleLineGroupInfo.mObject, inStartStation, inEndStation, g_reportFileName, oLinkCodesInfo.mCodeName)
        ProgressBar.Value = ProgressBar.Value + pbarInc
      
    Next

    'update progress bar
    ProgressBar.Value = 100

    ProgressBar.Visible = False
    progressBarLabel.Visible = False


    Call WriteReportFooter(g_reportFileName)
    
    OpenFileByDefaultBrowser g_reportFileName
    
End Sub

Private Sub CancelButton_Click()

    Unload Me

End Sub

Private Sub UserForm_Terminate()

    ' clean up created objects
    Set g_oCivilApp = Nothing
    Set g_oAeccDb = Nothing
    Set g_oCivilRoadwayApp = Nothing
    Set g_oRoadwayDocument = Nothing
    Set g_Corridors = Nothing
    Set g_oSlopeStakeData = Nothing

End Sub

Private Sub ListView_ItemClick(ByVal item As ListItem)
    If MultiItemsSelected = True Then
        StartStaEdit.Enabled = False
        EndStaEdit.Enabled = False
    Else
        Dim oSampleLineGroupInfo As CSampleLineGroup
        Dim dStartStation As Double, dEndStation As Double
        Set oSampleLineGroupInfo = FindSampleLineGroupInfo(item.Text, _
                                                           item.SubItems(nAlignmentIndex), _
                                                           item.SubItems(nSampleLineGroup))
        Call StartStationOfSampleLineGroup(oSampleLineGroupInfo.mObject, dStartStation, dEndStation)
        Set g_StationInfo.oSampleLineGroup = oSampleLineGroupInfo.mObject
        g_StationInfo.index = item.index
        g_StationInfo.startStation = GetRawStation(oSampleLineGroupInfo.mObject.Parent.GetStationStringWithEquations(dStartStation))
        g_StationInfo.endStation = GetRawStation(oSampleLineGroupInfo.mObject.Parent.GetStationStringWithEquations(dEndStation))
        g_StationInfo.curStartStation = GetRawStation(item.SubItems(nStationStartIndex))
        g_StationInfo.curEndStation = GetRawStation(item.SubItems(nStationEndIndex))
        StartStaEdit.Enabled = True
        EndStaEdit.Enabled = True
        StartStaEdit.Value = item.SubItems(nStationStartIndex)
        EndStaEdit.Value = item.SubItems(nStationEndIndex)
    End If
End Sub

Private Sub EndStaEdit_Change()
    Dim curListItem As ListItem
    Set curListItem = ListView.SelectedItem
    If Not curListItem Is Nothing Then
        curListItem.SubItems(nStationEndIndex) = EndStaEdit.Value
    End If
End Sub

Private Sub EndStaEdit_Exit(ByVal Cancel As MSForms.ReturnBoolean)
    On Error Resume Next
    Dim oAlignment As AeccAlignment
    Dim rawStation As Double
    Dim curListItem As ListItem

    Set curListItem = ListView.SelectedItem
    If curListItem Is Nothing Then
       StartStaEdit.Value = ""
       Exit Sub
    End If
    Set oAlignment = g_StationInfo.oSampleLineGroup.Parent
    'verify the station is in right format
    rawStation = CDbl(EndStaEdit.Value)
    If Err Then
        Err.Clear
        rawStation = GetRawStation(EndStaEdit.Value)
        If Err Then
            MsgBox "Please input right format for station."
            rawStation = g_StationInfo.curEndStation
        End If
    End If

    'verify the startStation >= default value
    If rawStation > g_StationInfo.endStation Or rawStation < g_StationInfo.curStartStation Then
        MsgBox "The EndStation Value is out of range"
        rawStation = g_StationInfo.endStation
    End If
    g_StationInfo.curEndStation = rawStation
    EndStaEdit.Value = oAlignment.GetStationStringWithEquations(rawStation)
End Sub

Private Sub EndStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub

Private Sub StartStaEdit_Change()
    Dim curListItem As ListItem
    Set curListItem = ListView.SelectedItem
    If Not curListItem Is Nothing Then
        curListItem.SubItems(nStationStartIndex) = StartStaEdit.Value
    End If
End Sub

Private Sub StartStaEdit_Exit(ByVal Cancel As MSForms.ReturnBoolean)
    On Error Resume Next
    Dim oAlignment As AeccAlignment
    Dim rawStation As Double
    Dim curListItem As ListItem

    Set curListItem = ListView.SelectedItem
    If curListItem Is Nothing Then
       StartStaEdit.Value = ""
       Exit Sub
    End If

    Set oAlignment = g_StationInfo.oSampleLineGroup.Parent
    'verify the station is in right format
    rawStation = CDbl(StartStaEdit.Value)
    If Err Then
        Err.Clear
        rawStation = GetRawStation(StartStaEdit.Value)
        If Err Then
            MsgBox "Please input right format for station."
            rawStation = g_StationInfo.curStartStation
        End If
    End If

    'verify the startStation >= default value
    If rawStation > g_StationInfo.curEndStation Or rawStation < g_StationInfo.startStation Then
        MsgBox "The StartStation Value is out of range"
        rawStation = g_StationInfo.startStation
    End If
    g_StationInfo.curStartStation = rawStation
    StartStaEdit.Value = oAlignment.GetStationStringWithEquations(rawStation)
End Sub



Private Sub StartStaEdit_KeyPress(ByVal KeyAscii As MSForms.ReturnInteger)
    If KeyAscii <> 8 And (KeyAscii < 48 Or KeyAscii > 57) And KeyAscii <> 46 And KeyAscii <> Asc("+") And KeyAscii <> Asc("-") Then
        Beep
        KeyAscii = 0
    End If
End Sub

Private Sub Frame3_Exit(ByVal Cancel As MSForms.ReturnBoolean)
    If Frame3.ActiveControl = StartStaEdit Then
        StartStaEdit_Exit Cancel
    ElseIf Frame3.ActiveControl = EndStaEdit Then
        EndStaEdit_Exit Cancel
    End If
End Sub


Private Sub FileSelectionButton_Click()

    Dim fileDialog As New CFileDialog
    
    With fileDialog

        .DefaultExt = "html"

        .DialogTitle = "Select a HTML File"

        .Filter = "HTML Files|*.HTML"

        .FilterIndex = 1

        .MaxFileSize = 255

        .FileName = g_reportFileName

        If .Show(True) Then

            g_reportFileName = fileDialog.FileName
            ReportFileNameEdit.Text = g_reportFileName

        Else

            Exit Sub

        End If

    End With

End Sub




Private Sub GetCaptions()
    ReDim sCaptionArr(nLastIndex)
 
    sCaptionArr(nNameIndex) = "Name"
    sCaptionArr(nAlignmentIndex) = "Alignment"
    sCaptionArr(nSampleLineGroup) = "Sample Line Group"
    sCaptionArr(nLinkCodes) = "Link"
    sCaptionArr(nStationStartIndex) = "Station Start"
    sCaptionArr(nStationEndIndex) = "Station End"
End Sub



'Get the start Station and end Station of the Sample Line Group. Assume that the lines in group are sorted.
' if there is no sampleline in group, the function return false and the startstation and endstation is invalid.
Public Function StartStationOfSampleLineGroup(oSampleLineGroup As AeccSampleLineGroup, dStartStation As Double, dEndStation As Double) As Boolean
    Dim oSampleLine As AeccSampleLine
    If oSampleLineGroup.SampleLines.count < 0 Then
        StartStationOfSampleLineGroup = False
    Else
        dStartStation = oSampleLineGroup.SampleLines(0).Station
        dEndStation = dStartStation
        StartStationOfSampleLineGroup = True
        For Each oSampleLine In oSampleLineGroup.SampleLines
            If oSampleLine.Station > dEndStation Then
                dEndStation = oSampleLine.Station
            End If
            If oSampleLine.Station < dStartStation Then
                dStartStation = oSampleLine.Station
            End If
        Next
    End If
    
End Function

Private Sub BuildCorridorInfo(oCorridor As AeccCorridor, oCorridorInfo As CCorridor)
    Dim dicBaselines As Dictionary
    Dim oBaselineInfo As CBaseline
    
    Dim oBaseline As AeccBaseline
    
    
    Set dicBaselines = oCorridorInfo.mBaselines
    Set oCorridorInfo.mObject = oCorridor
    dicBaselines.removeAll
    
    For Each oBaseline In oCorridor.Baselines
        If dicBaselines.Exists(oBaseline.Alignment.Name) = False Then
            Set oBaselineInfo = New CBaseline
            BuildBaselineInfo oCorridor, oBaseline, oBaselineInfo
            dicBaselines.Add oBaseline.Alignment.Name, oBaselineInfo
        End If
    Next
End Sub
Private Sub BuildBaselineInfo(oCorridor As AeccCorridor, oBaseline As AeccBaseline, oBaselineInfo As CBaseline)
    Dim dicSampleLineGroups As Dictionary
    Dim oSampleLineGroupInfo As CSampleLineGroup
    
    Dim oSampleLineGroup As AeccSampleLineGroup
    Dim oBaselineRegion As AeccBaselineRegion
    
    Set dicSampleLineGroups = oBaselineInfo.mSampleLineGroups
    Set oBaselineInfo.mObject = oBaseline
    dicSampleLineGroups.removeAll
    
    Dim dicLinkCodesGroups As Dictionary
    Dim oLinkCodesInfo As CLinkCodes
    Set dicLinkCodesGroups = oBaselineInfo.mLinkCodesGroups
    Set oBaselineInfo.mObject = oBaseline
    dicLinkCodesGroups.removeAll
    
    If oBaseline.Alignment.SampleLineGroups.count > 0 And oBaseline.BaselineRegions.count > 0 Then
        For Each oSampleLineGroup In oBaseline.Alignment.SampleLineGroups
            If dicSampleLineGroups.Exists(oSampleLineGroup.Name) = False Then
                Set oSampleLineGroupInfo = New CSampleLineGroup
                Set oSampleLineGroupInfo.mObject = oSampleLineGroup
                dicSampleLineGroups.Add oSampleLineGroup.Name, oSampleLineGroupInfo
            End If
        Next
        
        Dim oSubAssembly As AeccSubassembly
        For Each oSubAssembly In g_oRoadwayDocument.Subassemblies
            Dim oRoadwayLinks As AeccRoadwayLinks
            Set oRoadwayLinks = oSubAssembly.Links
            Dim oRoadwayLink As AeccRoadwayLink
            For Each oRoadwayLink In oRoadwayLinks
                Dim iIndex As Integer
                For iIndex = 0 To oRoadwayLink.RoadwayCodes.count - 1
                    Dim sCodeName As String
                    sCodeName = oRoadwayLink.RoadwayCodes.item(iIndex)
                    If dicLinkCodesGroups.Exists(sCodeName) = False Then
                        Set oLinkCodesInfo = New CLinkCodes
                        oLinkCodesInfo.mCodeName = sCodeName
                        dicLinkCodesGroups.Add sCodeName, oLinkCodesInfo
                    End If
                Next iIndex
            Next
        Next
        
    End If
End Sub

Private Function FindSampleLineGroupInfo(sCorridor As String, sAlignment As String, sSampleLineGroupName As String) As CSampleLineGroup
    On Error GoTo ErrHandle
    Dim oCorridorInfo As CCorridor
    Dim oBaselineInfo As CBaseline
   
    Set oCorridorInfo = g_Corridors.item(sCorridor)
    Set oBaselineInfo = oCorridorInfo.mBaselines.item(sAlignment)
    Set FindSampleLineGroupInfo = oBaselineInfo.mSampleLineGroups.item(sSampleLineGroupName)
    
    Exit Function
ErrHandle:
    Set FindSampleLineGroupInfo = Nothing
End Function

Private Function FindLinkCodesInfo(sCorridor As String, sAlignment As String, sCodeName As String) As CLinkCodes
    On Error GoTo ErrHandle
    Dim oCorridorInfo As CCorridor
    Dim oBaselineInfo As CBaseline
   
    Set oCorridorInfo = g_Corridors.item(sCorridor)
    Set oBaselineInfo = oCorridorInfo.mBaselines.item(sAlignment)
    Set FindLinkCodesInfo = oBaselineInfo.mLinkCodesGroups.item(sCodeName)
    
    Exit Function
ErrHandle:
    Set FindLinkCodesInfo = Nothing
End Function

Private Function MultiItemsSelected() As Boolean
    Dim count As Integer
    Dim item As ListItem
    MultiItemsSelected = False
    For Each item In ListView.ListItems
        If item.Selected = True Then
            count = count + 1
        End If
        If count = 2 Then
            MultiItemsSelected = True
            Exit Function
        End If
    Next
End Function

Attribute VB_Name = "ReportWriter"
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'



Option Explicit
Function WriteReportHeader(rptName As String) As Boolean
    Dim str As String
    Dim unitsStr As String
    Dim fs
    Dim ts As TextStream
    
    'unitsStr = GetUnitStr
 
    Set fs = CreateObject("Scripting.FileSystemObject")
    Set ts = fs.CreateTextFile(rptName, True)
    
    
    str = "<HTML title='Corridor Slope Stake Report'><Body>"
    ts.WriteLine (str)
    ts.WriteLine ("<Body>")
    ts.WriteLine ("<center>")
    
    str = "<H1>Corridor Slope Stake Report</H1>"
    ts.WriteLine (str)
    ts.WriteLine ("</center>")
    
      
    
    ' write owner and client setting
    WriteUserSetting ts
    
    ' data info
    str = "Date: " & DateTime.Month(DateTime.Date) & "-" & DateTime.Day(DateTime.Date) & "-" & DateTime.Year(DateTime.Date) & "<br/>"
    ts.WriteLine (str)
    
    ts.WriteLine ("<HR/>")
    ts.Close

   
    Set fs = Nothing
    Set ts = Nothing
    
    
    WriteReportHeader = True
End Function

' Write the end of html file
Function WriteReportFooter(rptName As String) As Boolean
    Dim str As String
    Dim fs, ts
    
  
    Set fs = CreateObject("Scripting.FileSystemObject")
 
    Set ts = fs.OpenTextFile(rptName, ForAppending)
        
    str = "</Body></HTML>"
    
    ts.WriteLine (str)
    ts.Close

    Set ts = Nothing
    Set fs = Nothing
  

    WriteReportFooter = True
End Function

' Append one item's report to html file
Function AppendReport(oCorridor As AeccCorridor, oBaseline As AeccBaseline, oSampleLineGroup As AeccSampleLineGroup, stationStart As Double, stationEnd As Double, rptName As String, sCodeName As String) As Boolean
    Dim str As String
    Dim fs As FileSystemObject
    Dim ts As TextStream
    Dim oBaseAlignment As AeccAlignment
    Dim i As Integer
    Dim Stations As Variant
    Dim curStation As Double
    
    Set fs = CreateObject("Scripting.FileSystemObject")
    
    Set ts = fs.OpenTextFile(rptName, ForAppending)
    
    Set oBaseAlignment = oCorridor.Baselines(0).Alignment
    ' Corridor info
    str = "Corridor Name: " & oCorridor.Name & "<br/>"
    str = str & "Description: " & oCorridor.Description & "<br/>"
    str = str & "Base Alignment Name: " & oBaseAlignment.Name & "<br/>"
    str = str & "Sample Line Group Name: " & oSampleLineGroup.Name & "<br/>"
    str = str & "Link Code Name: " & sCodeName & "<br/>"
    str = str & "Station Range: " & "Start: " & oBaseAlignment.GetStationStringWithEquations(stationStart) _
                & ",  End: " & oBaseAlignment.GetStationStringWithEquations(stationEnd) & "<br/>"

    ts.WriteLine (str)
    
 
'    extract data
    Call ExtractData(oCorridor, oBaseline, oSampleLineGroup, stationStart, stationEnd, sCodeName)
    
    Stations = g_oSlopeStakeData.Keys
    For i = 0 To g_oSlopeStakeData.count - 1
        curStation = Stations(i)
        AppendSingleTable oCorridor, curStation, ts
    Next i
     
    ts.WriteLine ("<HR/>")
    ts.Close

    Set ts = Nothing
    Set fs = Nothing
    
    AppendReport = True
End Function

Private Sub AppendSingleTable(oCorridor As AeccCorridor, dStation As Double, ts As TextStream)
    Dim str As String
    Dim arrDataBySta As Variant
    Dim cLeftDatas As Dictionary
    Dim cRightDatas As Dictionary
    Dim arrLeftEndInfo As Variant
    Dim arrRightEndInfo As Variant
    
    Dim i As Long
    
    If Not g_oSlopeStakeData.Exists(dStation) Then
        Exit Sub
    End If
    
    arrDataBySta = g_oSlopeStakeData.item(dStation)
    Set cLeftDatas = arrDataBySta(nLeftIndex)
    Set cRightDatas = arrDataBySta(nRightIndex)
    arrLeftEndInfo = arrDataBySta(nLeftEndIndex)
    arrRightEndInfo = arrDataBySta(nRightEndIndex)
    
    ts.WriteLine ("<center>")
    str = oCorridor.Baselines(0).Alignment.Name & "<br/>"
    str = str & "Station: " & oCorridor.Baselines(0).Alignment.GetStationStringWithEquations(dStation)
    ts.WriteLine (str)
    
    ts.WriteLine ("</center>")
    str = "<br><table border='1' width='100%' id='table1'>"
    ts.WriteLine (str)
    
    i = 1
    
    Do
        Dim iRow As Long '1 based
        For iRow = 1 To 4
            Dim arrRowData(0 To 12) As String
            Erase arrRowData
            'leftend and rightend info
            If i = 1 And iRow < 4 Then
                arrRowData(0) = arrLeftEndInfo(iRow - 1)
                arrRowData(12) = arrRightEndInfo(iRow - 1)

            End If
            
            Dim iColum As Integer
            For iColum = 1 To 5
                Dim arrLeftData As Variant
                Dim arrRightData As Variant
                Dim nCurColIndex As Long '1 based
                'left side
                nCurColIndex = (i - 1) * 5 + iColum
                If nCurColIndex <= cLeftDatas.count Then
                
                    arrLeftData = cLeftDatas.Items(nCurColIndex - 1)
                    arrRowData(6 - iColum) = arrLeftData(iRow - 1)

                End If
                'right side
                If nCurColIndex <= cRightDatas.count Then
                    arrRightData = cRightDatas.Items(nCurColIndex - 1)
                    arrRowData(6 + iColum) = arrRightData(iRow - 1)

                End If
                
            Next iColum
            WriteOneTableRow arrRowData, ts
        Next iRow
        'seperate row
        Dim arrBlank(0 To 12) As String
        WriteOneTableRow arrBlank, ts
        i = i + 1
    Loop Until i * 5 >= (cLeftDatas.count + 5) Or i * 5 >= (cRightDatas.count + 5)
    
    ts.WriteLine ("</Table>")
    
End Sub

Private Sub WriteOneTableRow(arrData As Variant, ts As TextStream)
    Dim i As Long
    Dim str As String
    str = "<b><tr>"
    For i = LBound(arrData) To UBound(arrData)
        If arrData(i) = "" Then
            str = str & "<td>" & "&nbsp;" & "</td>"
        Else
            str = str & "<td>" & arrData(i) & "</td>"
        End If
    Next i
    str = str & "</tr></b>"
    ts.WriteLine (str)
    
End Sub

Attribute VB_Name = "ThisDrawing"
Attribute VB_Base = "0{7AABBB95-79BE-4C0F-8024-EB6AF271231C}"
Attribute VB_GlobalNameSpace = False
Attribute VB_Creatable = False
Attribute VB_PredeclaredId = True
Attribute VB_Exposed = True
Attribute VB_TemplateDerived = False
Attribute VB_Customizable = True
''//
''// (C) Copyright 2008 by Autodesk, Inc.
''//
''// Permission to use, copy, modify, and distribute this software in
''// object code form for any purpose and without fee is hereby granted,
''// provided that the above copyright notice appears in all copies and
''// that both that copyright notice and the limited warranty and
''// restricted rights notice below appear in all supporting
''// documentation.
''//
''// AUTODESK PROVIDES THIS PROGRAM "AS IS" AND WITH ALL FAULTS.
''// AUTODESK SPECIFICALLY DISCLAIMS ANY IMPLIED WARRANTY OF
''// MERCHANTABILITY OR FITNESS FOR A PARTICULAR USE.  AUTODESK, INC.
''// DOES NOT WARRANT THAT THE OPERATION OF THE PROGRAM WILL BE
''// UNINTERRUPTED OR ERROR FREE.
''//
''// Use, duplication, or disclosure by the U.S. Government is subject to
''// restrictions set forth in FAR 52.227-19 (Commercial Computer
''// Software - Restricted Rights) and DFAR 252.227-7013(c)(1)(ii)
''// (Rights in Technical Data and Computer Software), as applicable.
'
'
'

Option Explicit
'
'Main entry point for this reports application
'
Sub corridorSlopeStake_RunReport()
    On Error Resume Next
    
    Dim rptDlg As ReportForm_CorridorSlopeStake
    
    ' initialize C3D
    If InitCooridorApp = False Then
        Call MsgBox("Error: Unable to initialize Civil 3D Object Model", vbOKOnly, "Civil 3D Reports")
        Exit Sub
    End If
    
    On Error Resume Next
    Err.Clear
    ' Create report dialog and display it
    Set rptDlg = New ReportForm_CorridorSlopeStake
    If Err.Number <> 0 Then
        Exit Sub
    End If
    rptDlg.Show
    
    Set rptDlg = Nothing
End Sub
